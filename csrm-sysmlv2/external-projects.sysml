// Partial package stubs for the four project dependencies of Data.
// The last target is known only from the Cameo proxy embedded in the core archive.
package CSRMExternalProjects {
    package 'CSRM Reference Information2' {
        package 'CubeSat Reference Information' {
            @CSRMv1Metadata::ExternalProjectSource {
                sourceRef = "CSRM Reference Information2.mdzip#_19_0_3_2b0010b_1613258543334_43499_42727";
                projectId = "PROJECT-e2add1de-891e-49b9-a159-bd240a9bebfd";
                evidence = "shared model";
            }
        }
        package 'Unit Imports' {
            @CSRMv1Metadata::ExternalProjectSource {
                sourceRef = "CSRM Reference Information2.mdzip#_19_0_3_2b0010b_1613258521460_451037_13805";
                projectId = "PROJECT-e2add1de-891e-49b9-a159-bd240a9bebfd";
                evidence = "shared model";
            }
        }
    }
    package 'CSRM-Profile2' {
        package 'CSRM Profile' {
            @CSRMv1Metadata::ExternalProjectSource {
                sourceRef = "CSRM-Profile2.mdzip#_0";
                projectId = "PROJECT-19eb7ec7d7ca3d7678dc375699a22de";
                evidence = "shared model";
            }
        }
    }
    package 'CSRM Profile' {
        package 'Derived Properties' {
            @CSRMv1Metadata::ExternalProjectSource {
                sourceRef = "CSRM Profile.mdzip#_19_0_3_2b0010b_1614441650535_642789_2693";
                projectId = "PROJECT-5e6754f1-4590-475a-a81b-f80f8587ee98";
                evidence = "embedded proxy only";
            }
        }
    }
}
