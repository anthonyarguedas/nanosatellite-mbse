// Imported ValueTypes only. Source quantity kinds and units are metadata references.
package 'ISO-80000-Extension' {
    package 'Imperial Units & US Customary Units' {
        package 'Quantities' {
            package 'Length' {
                attribute def 'length[inch]' :> 'ISO-80000'::'ISO80000-3 Space and Time'::'Quantities'::'length'::'length' {
                    @CSRMv1Metadata::ValueTypeSource {
                        sourceRef = "ISO-80000-Extension.mdzip#_19_0beta_8a3027a_1504525646498_546513_41336";
                        quantityKindRef = "";
                        quantityKindName = "";
                        unitRef = "ISO-80000-Extension.mdzip#_19_0beta_8a3027a_1504624305111_59576_41755";
                        unitName = "ISO-80000-Extension::Imperial Units & US Customary Units::Units::Length::inch";
                    }
                }
                attribute def 'length[mile]' :> 'ISO-80000'::'ISO80000-3 Space and Time'::'Quantities'::'length'::'length' {
                    @CSRMv1Metadata::ValueTypeSource {
                        sourceRef = "ISO-80000-Extension.mdzip#_19_0beta_8a3027a_1504525651398_191029_41361";
                        quantityKindRef = "";
                        quantityKindName = "";
                        unitRef = "ISO-80000-Extension.mdzip#_19_0beta_8a3027a_1504685081619_417319_43911";
                        unitName = "ISO-80000-Extension::Imperial Units & US Customary Units::Units::Length::mile";
                    }
                }
                attribute def 'length[yard]' :> 'ISO-80000'::'ISO80000-3 Space and Time'::'Quantities'::'length'::'length' {
                    @CSRMv1Metadata::ValueTypeSource {
                        sourceRef = "ISO-80000-Extension.mdzip#_19_0beta_8a3027a_1504525653328_656601_41386";
                        quantityKindRef = "";
                        quantityKindName = "";
                        unitRef = "ISO-80000-Extension.mdzip#_19_0beta_8a3027a_1504684433940_736055_43523";
                        unitName = "ISO-80000-Extension::Imperial Units & US Customary Units::Units::Length::yard";
                    }
                }
                attribute def 'length[foot]' :> 'ISO-80000'::'ISO80000-3 Space and Time'::'Quantities'::'length'::'length' {
                    @CSRMv1Metadata::ValueTypeSource {
                        sourceRef = "ISO-80000-Extension.mdzip#_19_0beta_8a3027a_1504525655316_575263_41411";
                        quantityKindRef = "";
                        quantityKindName = "";
                        unitRef = "ISO-80000-Extension.mdzip#_19_0beta_8a3027a_1504625572044_214311_42431";
                        unitName = "ISO-80000-Extension::Imperial Units & US Customary Units::Units::Length::foot";
                    }
                }
            }
            package 'Area' {
                attribute def 'area[square inch]' :> 'ISO-80000'::'ISO80000-3 Space and Time'::'Quantities'::'area'::'area' {
                    @CSRMv1Metadata::ValueTypeSource {
                        sourceRef = "ISO-80000-Extension.mdzip#_19_0beta_8a3027a_1504686086128_760199_44860";
                        quantityKindRef = "";
                        quantityKindName = "";
                        unitRef = "ISO-80000-Extension.mdzip#_19_0beta_8a3027a_1504686507390_314871_45572";
                        unitName = "ISO-80000-Extension::Imperial Units & US Customary Units::Units::Area::square inch";
                    }
                }
                attribute def 'area[square foot]' :> 'ISO-80000'::'ISO80000-3 Space and Time'::'Quantities'::'area'::'area' {
                    @CSRMv1Metadata::ValueTypeSource {
                        sourceRef = "ISO-80000-Extension.mdzip#_19_0beta_8a3027a_1504686249978_876024_45473";
                        quantityKindRef = "";
                        quantityKindName = "";
                        unitRef = "ISO-80000-Extension.mdzip#_19_0beta_8a3027a_1504691387226_574354_45641";
                        unitName = "ISO-80000-Extension::Imperial Units & US Customary Units::Units::Area::square foot";
                    }
                }
                attribute def 'area[square yard]' :> 'ISO-80000'::'ISO80000-3 Space and Time'::'Quantities'::'area'::'area' {
                    @CSRMv1Metadata::ValueTypeSource {
                        sourceRef = "ISO-80000-Extension.mdzip#_19_0beta_8a3027a_1504686251515_123939_45478";
                        quantityKindRef = "";
                        quantityKindName = "";
                        unitRef = "ISO-80000-Extension.mdzip#_19_0beta_8a3027a_1504691951419_419111_45734";
                        unitName = "ISO-80000-Extension::Imperial Units & US Customary Units::Units::Area::square yard";
                    }
                }
                attribute def 'area[square mile]' :> 'ISO-80000'::'ISO80000-3 Space and Time'::'Quantities'::'area'::'area' {
                    @CSRMv1Metadata::ValueTypeSource {
                        sourceRef = "ISO-80000-Extension.mdzip#_19_0beta_8a3027a_1504686252158_600783_45483";
                        quantityKindRef = "";
                        quantityKindName = "";
                        unitRef = "ISO-80000-Extension.mdzip#_19_0beta_8a3027a_1504692577023_990967_45783";
                        unitName = "ISO-80000-Extension::Imperial Units & US Customary Units::Units::Area::square mile";
                    }
                }
                attribute def 'area[acre]' :> 'ISO-80000'::'ISO80000-3 Space and Time'::'Quantities'::'area'::'area' {
                    @CSRMv1Metadata::ValueTypeSource {
                        sourceRef = "ISO-80000-Extension.mdzip#_19_0beta_8a3027a_1504708818013_557107_48071";
                        quantityKindRef = "";
                        quantityKindName = "";
                        unitRef = "ISO-80000-Extension.mdzip#_19_0beta_8a3027a_1504708680381_877097_48039";
                        unitName = "ISO-80000-Extension::Imperial Units & US Customary Units::Units::Area::acre";
                    }
                }
            }
            package 'Volume' {
                attribute def 'volume[cubic inch]' :> 'ISO-80000'::'ISO80000-3 Space and Time'::'Quantities'::'volume'::'volume' {
                    @CSRMv1Metadata::ValueTypeSource {
                        sourceRef = "ISO-80000-Extension.mdzip#_19_0beta_8a3027a_1504699852137_374863_46743";
                        quantityKindRef = "";
                        quantityKindName = "";
                        unitRef = "ISO-80000-Extension.mdzip#_19_0beta_8a3027a_1504700199541_391030_46912";
                        unitName = "ISO-80000-Extension::Imperial Units & US Customary Units::Units::Volume::cubic inch";
                    }
                }
                attribute def 'volume[cubic foot]' :> 'ISO-80000'::'ISO80000-3 Space and Time'::'Quantities'::'volume'::'volume' {
                    @CSRMv1Metadata::ValueTypeSource {
                        sourceRef = "ISO-80000-Extension.mdzip#_19_0beta_8a3027a_1504699979949_209248_46802";
                        quantityKindRef = "";
                        quantityKindName = "";
                        unitRef = "ISO-80000-Extension.mdzip#_19_0beta_8a3027a_1504701732995_81019_47035";
                        unitName = "ISO-80000-Extension::Imperial Units & US Customary Units::Units::Volume::cubic foot";
                    }
                }
                attribute def 'volume[cubic yard]' :> 'ISO-80000'::'ISO80000-3 Space and Time'::'Quantities'::'volume'::'volume' {
                    @CSRMv1Metadata::ValueTypeSource {
                        sourceRef = "ISO-80000-Extension.mdzip#_19_0beta_8a3027a_1504699981222_481490_46807";
                        quantityKindRef = "";
                        quantityKindName = "";
                        unitRef = "ISO-80000-Extension.mdzip#_19_0beta_8a3027a_1504701993087_181365_47076";
                        unitName = "ISO-80000-Extension::Imperial Units & US Customary Units::Units::Volume::cubic yard";
                    }
                }
                attribute def 'volume[gallon (UK)]' :> 'ISO-80000'::'ISO80000-3 Space and Time'::'Quantities'::'volume'::'volume' {
                    @CSRMv1Metadata::ValueTypeSource {
                        sourceRef = "ISO-80000-Extension.mdzip#_19_0beta_8a3027a_1504764675651_603368_48752";
                        quantityKindRef = "";
                        quantityKindName = "";
                        unitRef = "ISO-80000-Extension.mdzip#_19_0beta_8a3027a_1504765726748_171036_49054";
                        unitName = "ISO-80000-Extension::Imperial Units & US Customary Units::Units::Volume::gallon (UK)";
                    }
                }
                attribute def 'volume[pint (UK)]' :> 'ISO-80000'::'ISO80000-3 Space and Time'::'Quantities'::'volume'::'volume' {
                    @CSRMv1Metadata::ValueTypeSource {
                        sourceRef = "ISO-80000-Extension.mdzip#_19_0beta_8a3027a_1504764770674_435105_48778";
                        quantityKindRef = "";
                        quantityKindName = "";
                        unitRef = "ISO-80000-Extension.mdzip#_19_0beta_8a3027a_1504766261201_145423_49104";
                        unitName = "ISO-80000-Extension::Imperial Units & US Customary Units::Units::Volume::pint (UK)";
                    }
                }
                attribute def 'volume[fluid ounce (UK)]' :> 'ISO-80000'::'ISO80000-3 Space and Time'::'Quantities'::'volume'::'volume' {
                    @CSRMv1Metadata::ValueTypeSource {
                        sourceRef = "ISO-80000-Extension.mdzip#_19_0beta_8a3027a_1504764772305_169520_48782";
                        quantityKindRef = "";
                        quantityKindName = "";
                        unitRef = "ISO-80000-Extension.mdzip#_19_0beta_8a3027a_1504765623215_705019_49022";
                        unitName = "ISO-80000-Extension::Imperial Units & US Customary Units::Units::Volume::fluid ounce (UK)";
                    }
                }
                attribute def 'volume[pint (US)]' :> 'ISO-80000'::'ISO80000-3 Space and Time'::'Quantities'::'volume'::'volume' {
                    @CSRMv1Metadata::ValueTypeSource {
                        sourceRef = "ISO-80000-Extension.mdzip#_19_0beta_8a3027a_1504765063997_277945_48902";
                        quantityKindRef = "";
                        quantityKindName = "";
                        unitRef = "ISO-80000-Extension.mdzip#_19_0beta_8a3027a_1504766607193_710737_49161";
                        unitName = "ISO-80000-Extension::Imperial Units & US Customary Units::Units::Volume::pint (US)";
                    }
                }
                attribute def 'volume[gallon (US)]' :> 'ISO-80000'::'ISO80000-3 Space and Time'::'Quantities'::'volume'::'volume' {
                    @CSRMv1Metadata::ValueTypeSource {
                        sourceRef = "ISO-80000-Extension.mdzip#_19_0beta_8a3027a_1504765063997_825857_48901";
                        quantityKindRef = "";
                        quantityKindName = "";
                        unitRef = "ISO-80000-Extension.mdzip#_19_0beta_8a3027a_1504766607193_11463_49160";
                        unitName = "ISO-80000-Extension::Imperial Units & US Customary Units::Units::Volume::gallon (US)";
                    }
                }
                attribute def 'volume[fluid ounce (US)]' :> 'ISO-80000'::'ISO80000-3 Space and Time'::'Quantities'::'volume'::'volume' {
                    @CSRMv1Metadata::ValueTypeSource {
                        sourceRef = "ISO-80000-Extension.mdzip#_19_0beta_8a3027a_1504765063997_860057_48900";
                        quantityKindRef = "";
                        quantityKindName = "";
                        unitRef = "ISO-80000-Extension.mdzip#_19_0beta_8a3027a_1504766607193_384679_49159";
                        unitName = "ISO-80000-Extension::Imperial Units & US Customary Units::Units::Volume::fluid ounce (US)";
                    }
                }
            }
            package 'Acceleration' {
                attribute def 'acceleration[foot per second squared]' :> 'ISO-80000'::'ISO80000-3 Space and Time'::'Quantities'::'acceleration'::'acceleration' {
                    @CSRMv1Metadata::ValueTypeSource {
                        sourceRef = "ISO-80000-Extension.mdzip#_19_0beta_8a3027a_1504702845502_790904_47208";
                        quantityKindRef = "";
                        quantityKindName = "";
                        unitRef = "ISO-80000-Extension.mdzip#_19_0beta_8a3027a_1504703304384_126512_47254";
                        unitName = "ISO-80000-Extension::Imperial Units & US Customary Units::Units::Acceleration::foot per second squared";
                    }
                }
            }
            package 'Speed and Velocity' {
                attribute def 'speed[foot per second]' :> 'ISO-80000'::'ISO80000-3 Space and Time'::'Quantities'::'speed'::'speed' {
                    @CSRMv1Metadata::ValueTypeSource {
                        sourceRef = "ISO-80000-Extension.mdzip#_19_0beta_8a3027a_1504704981209_503127_47460";
                        quantityKindRef = "";
                        quantityKindName = "";
                        unitRef = "ISO-80000-Extension.mdzip#_19_0beta_8a3027a_1504705827311_601119_47622";
                        unitName = "ISO-80000-Extension::Imperial Units & US Customary Units::Units::Speed and Velocity::foot per second";
                    }
                }
                attribute def 'speed[mile per hour]' :> 'ISO-80000'::'ISO80000-3 Space and Time'::'Quantities'::'speed'::'speed' {
                    @CSRMv1Metadata::ValueTypeSource {
                        sourceRef = "ISO-80000-Extension.mdzip#_19_0beta_8a3027a_1504705074051_445071_47511";
                        quantityKindRef = "";
                        quantityKindName = "";
                        unitRef = "ISO-80000-Extension.mdzip#_19_0beta_8a3027a_1504706181336_789466_47704";
                        unitName = "ISO-80000-Extension::Imperial Units & US Customary Units::Units::Speed and Velocity::mile per hour";
                    }
                }
                attribute def 'velocity[foot per second]' :> 'ISO-80000'::'ISO80000-3 Space and Time'::'Quantities'::'velocity'::'velocity' {
                    @CSRMv1Metadata::ValueTypeSource {
                        sourceRef = "ISO-80000-Extension.mdzip#_19_0beta_8a3027a_1504705396560_983648_47549";
                        quantityKindRef = "";
                        quantityKindName = "";
                        unitRef = "ISO-80000-Extension.mdzip#_19_0beta_8a3027a_1504705827311_601119_47622";
                        unitName = "ISO-80000-Extension::Imperial Units & US Customary Units::Units::Speed and Velocity::foot per second";
                    }
                }
                attribute def 'velocity[mile per hour]' :> 'ISO-80000'::'ISO80000-3 Space and Time'::'Quantities'::'velocity'::'velocity' {
                    @CSRMv1Metadata::ValueTypeSource {
                        sourceRef = "ISO-80000-Extension.mdzip#_19_0beta_8a3027a_1504705408790_942431_47554";
                        quantityKindRef = "";
                        quantityKindName = "";
                        unitRef = "ISO-80000-Extension.mdzip#_19_0beta_8a3027a_1504706181336_789466_47704";
                        unitName = "ISO-80000-Extension::Imperial Units & US Customary Units::Units::Speed and Velocity::mile per hour";
                    }
                }
            }
            package 'Mass' {
                attribute def 'mass[ounce]' :> 'ISO-80000'::'ISO80000-4 Mechanics'::'Quantities'::'mass'::'mass' {
                    @CSRMv1Metadata::ValueTypeSource {
                        sourceRef = "ISO-80000-Extension.mdzip#_19_0beta_8a3027a_1504768654855_543874_49487";
                        quantityKindRef = "";
                        quantityKindName = "";
                        unitRef = "ISO-80000-Extension.mdzip#_19_0beta_8a3027a_1504768690555_242296_49519";
                        unitName = "ISO-80000-Extension::Imperial Units & US Customary Units::Units::Mass::ounce";
                    }
                }
                attribute def 'mass[pound]' :> 'ISO-80000'::'ISO80000-4 Mechanics'::'Quantities'::'mass'::'mass' {
                    @CSRMv1Metadata::ValueTypeSource {
                        sourceRef = "ISO-80000-Extension.mdzip#_19_0beta_8c4028a_1504269313690_855494_12897";
                        quantityKindRef = "";
                        quantityKindName = "";
                        unitRef = "ISO-80000-Extension.mdzip#_19_0beta_8a3027a_1504768544760_911432_49458";
                        unitName = "ISO-80000-Extension::Imperial Units & US Customary Units::Units::Mass::pound";
                    }
                }
            }
        }
    }
    package 'Nautical Units' {
        package 'Quantities' {
            package 'Length' {
                attribute def 'length[nautical mile]' :> 'ISO-80000'::'ISO80000-3 Space and Time'::'Quantities'::'length'::'length' {
                    @CSRMv1Metadata::ValueTypeSource {
                        sourceRef = "ISO-80000-Extension.mdzip#_19_0beta_8a3027a_1504762833653_848553_48268";
                        quantityKindRef = "";
                        quantityKindName = "";
                        unitRef = "ISO-80000-Extension.mdzip#_19_0beta_8a3027a_1504763229219_966732_48397";
                        unitName = "ISO-80000-Extension::Nautical Units::Units::Length::nautical mile";
                    }
                }
            }
            package 'Speed and Velocity' {
                attribute def 'speed[knot]' :> 'ISO-80000'::'ISO80000-3 Space and Time'::'Quantities'::'length'::'length', 'ISO-80000'::'ISO80000-3 Space and Time'::'Quantities'::'speed'::'speed' {
                    @CSRMv1Metadata::ValueTypeSource {
                        sourceRef = "ISO-80000-Extension.mdzip#_19_0beta_8a3027a_1504763086333_87751_48360";
                        quantityKindRef = "";
                        quantityKindName = "";
                        unitRef = "ISO-80000-Extension.mdzip#_19_0beta_8a3027a_1504763480637_386422_48440";
                        unitName = "ISO-80000-Extension::Nautical Units::Units::Speed and Velocity::knot";
                    }
                }
            }
        }
    }
    package 'Common Units' {
        package 'Quantities' {
            package 'Speed and Velocity' {
                attribute def 'speed[kilometre per hour]' :> 'ISO-80000'::'ISO80000-3 Space and Time'::'Quantities'::'speed'::'speed' {
                    @CSRMv1Metadata::ValueTypeSource {
                        sourceRef = "ISO-80000-Extension.mdzip#_19_0beta_8a3027a_1505813200349_817015_83662";
                        quantityKindRef = "";
                        quantityKindName = "";
                        unitRef = "ISO-80000-Extension.mdzip#_19_0beta_8a3027a_1505814555598_352719_41820";
                        unitName = "ISO-80000-Extension::Common Units::Units::Speed and Velocity::kilometre per hour";
                    }
                }
                attribute def 'velocity[kilometre per hour]' :> 'ISO-80000'::'ISO80000-3 Space and Time'::'Quantities'::'velocity'::'velocity' {
                    @CSRMv1Metadata::ValueTypeSource {
                        sourceRef = "ISO-80000-Extension.mdzip#_19_0beta_8a3027a_1505816028867_649774_42101";
                        quantityKindRef = "";
                        quantityKindName = "";
                        unitRef = "ISO-80000-Extension.mdzip#_19_0beta_8a3027a_1505814555598_352719_41820";
                        unitName = "ISO-80000-Extension::Common Units::Units::Speed and Velocity::kilometre per hour";
                    }
                }
            }
            package 'Volume' {
                attribute def 'volume[litre]' :> 'ISO-80000'::'ISO80000-3 Space and Time'::'Quantities'::'volume'::'volume' {
                    @CSRMv1Metadata::ValueTypeSource {
                        sourceRef = "ISO-80000-Extension.mdzip#_19_0beta_8a3027a_1506083377553_418334_13278";
                        quantityKindRef = "";
                        quantityKindName = "";
                        unitRef = "";
                        unitName = "";
                    }
                }
            }
        }
    }
}
