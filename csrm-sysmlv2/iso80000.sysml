// Imported ValueTypes only. Source quantity kinds and units are metadata references.
package 'ISO-80000' {
    package 'IEC80000-6 Electromagnetism' {
        package 'Quantities' {
            package 'electric current' {
                attribute def 'electric current[milliampere]' :> 'ISO-80000'::'IEC80000-6 Electromagnetism'::'Quantities'::'electric current'::'electric current' {
                    @CSRMv1Metadata::ValueTypeSource {
                        sourceRef = "ISO-80000.mdzip#_18_0beta_903028d_1388650176009_428066_46312";
                        quantityKindRef = "ISO-80000.mdzip#_18_0beta_903028d_1388650177984_818614_51788";
                        quantityKindName = "ISO-80000::IEC80000-6 Electromagnetism::Quantities::electric current::electric current";
                        unitRef = "ISO-80000.mdzip#_18_0beta_903028d_1388650198270_13403_167318";
                        unitName = "ISO-80000::IEC80000-6 Electromagnetism::Units::ampere::milliampere";
                    }
                }
                attribute def 'electric current' {
                    @CSRMv1Metadata::ValueTypeSource {
                        sourceRef = "ISO-80000.mdzip#_18_0beta_903028d_1388650188627_40055_110473";
                        quantityKindRef = "ISO-80000.mdzip#_18_0beta_903028d_1388650177984_818614_51788";
                        quantityKindName = "ISO-80000::IEC80000-6 Electromagnetism::Quantities::electric current::electric current";
                        unitRef = "";
                        unitName = "";
                    }
                }
                attribute def 'electric current[ampere]' :> 'ISO-80000'::'IEC80000-6 Electromagnetism'::'Quantities'::'electric current'::'electric current' {
                    @CSRMv1Metadata::ValueTypeSource {
                        sourceRef = "ISO-80000.mdzip#_18_0beta_903028d_1388650189201_296142_113251";
                        quantityKindRef = "ISO-80000.mdzip#_18_0beta_903028d_1388650177984_818614_51788";
                        quantityKindName = "ISO-80000::IEC80000-6 Electromagnetism::Quantities::electric current::electric current";
                        unitRef = "ISO-80000.mdzip#_18_0beta_903028d_1388650191722_837876_127168";
                        unitName = "ISO-80000::IEC80000-6 Electromagnetism::Units::ampere::ampere";
                    }
                }
            }
            package 'electric current density' {
                attribute def 'electric current density[ampere per square metre]' :> 'ISO-80000'::'IEC80000-6 Electromagnetism'::'Quantities'::'electric current density'::'electric current density' {
                    @CSRMv1Metadata::ValueTypeSource {
                        sourceRef = "ISO-80000.mdzip#_18_0beta_903028d_1388650185648_30703_98522";
                        quantityKindRef = "ISO-80000.mdzip#_18_0beta_903028d_1388650190935_289728_121833";
                        quantityKindName = "ISO-80000::IEC80000-6 Electromagnetism::Quantities::electric current density::electric current density";
                        unitRef = "ISO-80000.mdzip#_18_0beta_903028d_1388650186090_285445_101687";
                        unitName = "ISO-80000::IEC80000-6 Electromagnetism::Units::ampere per square metre::ampere per square metre";
                    }
                }
                attribute def 'electric current density' {
                    @CSRMv1Metadata::ValueTypeSource {
                        sourceRef = "ISO-80000.mdzip#_18_0beta_903028d_1388650198783_26818_170324";
                        quantityKindRef = "ISO-80000.mdzip#_18_0beta_903028d_1388650190935_289728_121833";
                        quantityKindName = "ISO-80000::IEC80000-6 Electromagnetism::Quantities::electric current density::electric current density";
                        unitRef = "";
                        unitName = "";
                    }
                }
            }
            package 'magnetic field strength' {
                attribute def 'magnetic field strength' {
                    @CSRMv1Metadata::ValueTypeSource {
                        sourceRef = "ISO-80000.mdzip#_18_0beta_903028d_1388650188402_442957_108344";
                        quantityKindRef = "ISO-80000.mdzip#_18_0beta_903028d_1388650182542_618534_80858";
                        quantityKindName = "ISO-80000::IEC80000-6 Electromagnetism::Quantities::magnetic field strength::magnetic field strength";
                        unitRef = "";
                        unitName = "";
                    }
                }
                attribute def 'magnetic field strength[ampere per metre]' :> 'ISO-80000'::'IEC80000-6 Electromagnetism'::'Quantities'::'magnetic field strength'::'magnetic field strength' {
                    @CSRMv1Metadata::ValueTypeSource {
                        sourceRef = "ISO-80000.mdzip#_18_0beta_903028d_1388650194403_461525_142281";
                        quantityKindRef = "ISO-80000.mdzip#_18_0beta_903028d_1388650182542_618534_80858";
                        quantityKindName = "ISO-80000::IEC80000-6 Electromagnetism::Quantities::magnetic field strength::magnetic field strength";
                        unitRef = "ISO-80000.mdzip#_18_0beta_903028d_1388650196871_395455_158389";
                        unitName = "ISO-80000::IEC80000-6 Electromagnetism::Units::ampere per metre::ampere per metre";
                    }
                }
            }
        }
    }
    package 'ISO80000-3 Space and Time' {
        package 'Quantities' {
            package 'length' {
                attribute def 'length[kilometre]' :> 'ISO-80000'::'ISO80000-3 Space and Time'::'Quantities'::'length'::'length' {
                    @CSRMv1Metadata::ValueTypeSource {
                        sourceRef = "ISO-80000.mdzip#_18_0beta_903028d_1388650176685_831550_48171";
                        quantityKindRef = "ISO-80000.mdzip#_18_0beta_903028d_1388650203142_138723_189255";
                        quantityKindName = "ISO-80000::ISO80000-3 Space and Time::Quantities::length::length";
                        unitRef = "ISO-80000.mdzip#_18_0beta_903028d_1388650193650_318017_138567";
                        unitName = "ISO-80000::ISO80000-3 Space and Time::Units::metre::kilometre";
                    }
                }
                attribute def 'length[metre]' :> 'ISO-80000'::'ISO80000-3 Space and Time'::'Quantities'::'length'::'length' {
                    @CSRMv1Metadata::ValueTypeSource {
                        sourceRef = "ISO-80000.mdzip#_18_0beta_903028d_1388650184197_68200_89010";
                        quantityKindRef = "ISO-80000.mdzip#_18_0beta_903028d_1388650203142_138723_189255";
                        quantityKindName = "ISO-80000::ISO80000-3 Space and Time::Quantities::length::length";
                        unitRef = "ISO-80000.mdzip#_18_0beta_903028d_1388650196337_288372_154784";
                        unitName = "ISO-80000::ISO80000-3 Space and Time::Units::metre::metre";
                    }
                }
                attribute def 'length[nanometre]' :> 'ISO-80000'::'ISO80000-3 Space and Time'::'Quantities'::'length'::'length' {
                    @CSRMv1Metadata::ValueTypeSource {
                        sourceRef = "ISO-80000.mdzip#_18_0beta_903028d_1388650186361_504568_102985";
                        quantityKindRef = "ISO-80000.mdzip#_18_0beta_903028d_1388650203142_138723_189255";
                        quantityKindName = "ISO-80000::ISO80000-3 Space and Time::Quantities::length::length";
                        unitRef = "ISO-80000.mdzip#_18_0beta_903028d_1388650194613_350097_143754";
                        unitName = "ISO-80000::ISO80000-3 Space and Time::Units::metre::nanometre";
                    }
                }
                attribute def 'length[millimetre]' :> 'ISO-80000'::'ISO80000-3 Space and Time'::'Quantities'::'length'::'length' {
                    @CSRMv1Metadata::ValueTypeSource {
                        sourceRef = "ISO-80000.mdzip#_18_0beta_903028d_1388650188500_264415_109792";
                        quantityKindRef = "ISO-80000.mdzip#_18_0beta_903028d_1388650203142_138723_189255";
                        quantityKindName = "ISO-80000::ISO80000-3 Space and Time::Quantities::length::length";
                        unitRef = "ISO-80000.mdzip#_18_0beta_903028d_1388650195769_306999_151309";
                        unitName = "ISO-80000::ISO80000-3 Space and Time::Units::metre::millimetre";
                    }
                }
                attribute def 'length' {
                    @CSRMv1Metadata::ValueTypeSource {
                        sourceRef = "ISO-80000.mdzip#_18_0beta_903028d_1388650194122_562877_140708";
                        quantityKindRef = "ISO-80000.mdzip#_18_0beta_903028d_1388650203142_138723_189255";
                        quantityKindName = "ISO-80000::ISO80000-3 Space and Time::Quantities::length::length";
                        unitRef = "";
                        unitName = "";
                    }
                }
                attribute def 'length[centimetre]' :> 'ISO-80000'::'ISO80000-3 Space and Time'::'Quantities'::'length'::'length' {
                    @CSRMv1Metadata::ValueTypeSource {
                        sourceRef = "ISO-80000.mdzip#_18_0beta_903028d_1388650197507_72058_162360";
                        quantityKindRef = "ISO-80000.mdzip#_18_0beta_903028d_1388650203142_138723_189255";
                        quantityKindName = "ISO-80000::ISO80000-3 Space and Time::Quantities::length::length";
                        unitRef = "ISO-80000.mdzip#_18_0beta_903028d_1388650190842_483494_121333";
                        unitName = "ISO-80000::ISO80000-3 Space and Time::Units::metre::centimetre";
                    }
                }
                attribute def 'length[decimetre]' :> 'ISO-80000'::'ISO80000-3 Space and Time'::'Quantities'::'length'::'length' {
                    @CSRMv1Metadata::ValueTypeSource {
                        sourceRef = "ISO-80000.mdzip#_18_0beta_903028d_1388650197817_764941_164038";
                        quantityKindRef = "ISO-80000.mdzip#_18_0beta_903028d_1388650203142_138723_189255";
                        quantityKindName = "ISO-80000::ISO80000-3 Space and Time::Quantities::length::length";
                        unitRef = "ISO-80000.mdzip#_18_0beta_903028d_1388650202381_707841_185493";
                        unitName = "ISO-80000::ISO80000-3 Space and Time::Units::metre::decimetre";
                    }
                }
            }
            package 'speed' {
                attribute def 'speed[metre per second]' :> 'ISO-80000'::'ISO80000-3 Space and Time'::'Quantities'::'speed'::'speed' {
                    @CSRMv1Metadata::ValueTypeSource {
                        sourceRef = "ISO-80000.mdzip#_18_0beta_903028d_1388650180999_872881_71027";
                        quantityKindRef = "ISO-80000.mdzip#_18_0beta_903028d_1388650189723_679589_115789";
                        quantityKindName = "ISO-80000::ISO80000-3 Space and Time::Quantities::speed::speed";
                        unitRef = "ISO-80000.mdzip#_18_0beta_903028d_1388650190442_674483_119618";
                        unitName = "ISO-80000::ISO80000-3 Space and Time::Units::metre per second::metre per second";
                    }
                }
                attribute def 'speed' {
                    @CSRMv1Metadata::ValueTypeSource {
                        sourceRef = "ISO-80000.mdzip#_18_0beta_903028d_1388650203108_876922_189119";
                        quantityKindRef = "ISO-80000.mdzip#_18_0beta_903028d_1388650189723_679589_115789";
                        quantityKindName = "ISO-80000::ISO80000-3 Space and Time::Quantities::speed::speed";
                        unitRef = "";
                        unitName = "";
                    }
                }
            }
            package 'area' {
                attribute def 'area[square metre]' :> 'ISO-80000'::'ISO80000-3 Space and Time'::'Quantities'::'area'::'area' {
                    @CSRMv1Metadata::ValueTypeSource {
                        sourceRef = "ISO-80000.mdzip#_18_0beta_903028d_1388650181697_71046_76139";
                        quantityKindRef = "ISO-80000.mdzip#_18_0beta_903028d_1388650192350_683466_131745";
                        quantityKindName = "ISO-80000::ISO80000-3 Space and Time::Quantities::area::area";
                        unitRef = "ISO-80000.mdzip#_18_0beta_903028d_1388650201188_399350_183791";
                        unitName = "ISO-80000::ISO80000-3 Space and Time::Units::square metre::square metre";
                    }
                }
                attribute def 'area' {
                    @CSRMv1Metadata::ValueTypeSource {
                        sourceRef = "ISO-80000.mdzip#_18_0beta_903028d_1388650185460_822442_97222";
                        quantityKindRef = "ISO-80000.mdzip#_18_0beta_903028d_1388650192350_683466_131745";
                        quantityKindName = "ISO-80000::ISO80000-3 Space and Time::Quantities::area::area";
                        unitRef = "";
                        unitName = "";
                    }
                }
            }
            package 'time' {
                attribute def 'time' {
                    @CSRMv1Metadata::ValueTypeSource {
                        sourceRef = "ISO-80000.mdzip#_18_0beta_903028d_1388650188512_144339_109917";
                        quantityKindRef = "ISO-80000.mdzip#_18_0beta_903028d_1388650203007_614025_188569";
                        quantityKindName = "ISO-80000::ISO80000-3 Space and Time::Quantities::time::time";
                        unitRef = "";
                        unitName = "";
                    }
                }
                attribute def 'time[second]' :> 'ISO-80000'::'ISO80000-3 Space and Time'::'Quantities'::'time'::'time' {
                    @CSRMv1Metadata::ValueTypeSource {
                        sourceRef = "ISO-80000.mdzip#_18_0beta_903028d_1388650198891_148719_170889";
                        quantityKindRef = "ISO-80000.mdzip#_18_0beta_903028d_1388650203007_614025_188569";
                        quantityKindName = "ISO-80000::ISO80000-3 Space and Time::Quantities::time::time";
                        unitRef = "ISO-80000.mdzip#_18_0beta_903028d_1388650185362_459589_96773";
                        unitName = "ISO-80000::ISO80000-3 Space and Time::Units::second::second";
                    }
                }
            }
            package 'acceleration' {
                attribute def 'acceleration' {
                    @CSRMv1Metadata::ValueTypeSource {
                        sourceRef = "ISO-80000.mdzip#_18_0beta_903028d_1388650189153_746526_112836";
                        quantityKindRef = "ISO-80000.mdzip#_18_0beta_903028d_1388650197853_429881_164274";
                        quantityKindName = "ISO-80000::ISO80000-3 Space and Time::Quantities::acceleration::acceleration";
                        unitRef = "";
                        unitName = "";
                    }
                }
                attribute def 'acceleration[metre per second squared]' :> 'ISO-80000'::'ISO80000-3 Space and Time'::'Quantities'::'acceleration'::'acceleration' {
                    @CSRMv1Metadata::ValueTypeSource {
                        sourceRef = "ISO-80000.mdzip#_18_0beta_903028d_1388650198064_856347_165513";
                        quantityKindRef = "ISO-80000.mdzip#_18_0beta_903028d_1388650197853_429881_164274";
                        quantityKindName = "ISO-80000::ISO80000-3 Space and Time::Quantities::acceleration::acceleration";
                        unitRef = "ISO-80000.mdzip#_18_0beta_903028d_1388650190255_158246_118982";
                        unitName = "ISO-80000::ISO80000-3 Space and Time::Units::metre per second squared::metre per second squared";
                    }
                }
            }
            package 'volume' {
                attribute def 'volume' {
                    @CSRMv1Metadata::ValueTypeSource {
                        sourceRef = "ISO-80000.mdzip#_18_0beta_903028d_1388650191667_380508_126546";
                        quantityKindRef = "ISO-80000.mdzip#_18_0beta_903028d_1388650197454_615753_162141";
                        quantityKindName = "ISO-80000::ISO80000-3 Space and Time::Quantities::volume::volume";
                        unitRef = "";
                        unitName = "";
                    }
                }
                attribute def 'volume[cubic metre]' :> 'ISO-80000'::'ISO80000-3 Space and Time'::'Quantities'::'volume'::'volume' {
                    @CSRMv1Metadata::ValueTypeSource {
                        sourceRef = "ISO-80000.mdzip#_18_0beta_903028d_1388650198447_465711_168384";
                        quantityKindRef = "ISO-80000.mdzip#_18_0beta_903028d_1388650197454_615753_162141";
                        quantityKindName = "ISO-80000::ISO80000-3 Space and Time::Quantities::volume::volume";
                        unitRef = "ISO-80000.mdzip#_18_0beta_903028d_1388650192799_840125_134635";
                        unitName = "ISO-80000::ISO80000-3 Space and Time::Units::cubic metre::cubic metre";
                    }
                }
            }
            package 'velocity' {
                attribute def 'velocity[metre per second]' :> 'ISO-80000'::'ISO80000-3 Space and Time'::'Quantities'::'velocity'::'velocity' {
                    @CSRMv1Metadata::ValueTypeSource {
                        sourceRef = "ISO-80000.mdzip#_18_0beta_903028d_1388650193281_622367_136704";
                        quantityKindRef = "ISO-80000.mdzip#_18_0beta_903028d_1388650180763_629699_69295";
                        quantityKindName = "ISO-80000::ISO80000-3 Space and Time::Quantities::velocity::velocity";
                        unitRef = "ISO-80000.mdzip#_18_0beta_903028d_1388650190442_674483_119618";
                        unitName = "ISO-80000::ISO80000-3 Space and Time::Units::metre per second::metre per second";
                    }
                }
                attribute def 'velocity' {
                    @CSRMv1Metadata::ValueTypeSource {
                        sourceRef = "ISO-80000.mdzip#_18_0beta_903028d_1388650203184_691120_189384";
                        quantityKindRef = "ISO-80000.mdzip#_18_0beta_903028d_1388650180763_629699_69295";
                        quantityKindName = "ISO-80000::ISO80000-3 Space and Time::Quantities::velocity::velocity";
                        unitRef = "";
                        unitName = "";
                    }
                }
            }
        }
    }
    package 'ISO80000-4 Mechanics' {
        package 'Quantities' {
            package 'mass density' {
                attribute def 'mass density[kilogram per cubic metre]' :> 'ISO-80000'::'ISO80000-4 Mechanics'::'Quantities'::'mass density'::'mass density' {
                    @CSRMv1Metadata::ValueTypeSource {
                        sourceRef = "ISO-80000.mdzip#_18_0beta_903028d_1388650178558_159802_54381";
                        quantityKindRef = "ISO-80000.mdzip#_18_0beta_903028d_1388650195338_128348_148283";
                        quantityKindName = "ISO-80000::ISO80000-4 Mechanics::Quantities::mass density::mass density";
                        unitRef = "ISO-80000.mdzip#_18_0beta_903028d_1388650181385_995041_73395";
                        unitName = "ISO-80000::ISO80000-4 Mechanics::Units::kilogram per cubic metre::kilogram per cubic metre";
                    }
                }
                attribute def 'mass density' {
                    @CSRMv1Metadata::ValueTypeSource {
                        sourceRef = "ISO-80000.mdzip#_18_0beta_903028d_1388650192872_357244_134795";
                        quantityKindRef = "ISO-80000.mdzip#_18_0beta_903028d_1388650195338_128348_148283";
                        quantityKindName = "ISO-80000::ISO80000-4 Mechanics::Quantities::mass density::mass density";
                        unitRef = "";
                        unitName = "";
                    }
                }
            }
            package 'mass' {
                attribute def 'mass[milligram]' :> 'ISO-80000'::'ISO80000-4 Mechanics'::'Quantities'::'mass'::'mass' {
                    @CSRMv1Metadata::ValueTypeSource {
                        sourceRef = "ISO-80000.mdzip#_18_0beta_903028d_1388650179955_769911_61861";
                        quantityKindRef = "ISO-80000.mdzip#_18_0beta_903028d_1388650182002_641636_78041";
                        quantityKindName = "ISO-80000::ISO80000-4 Mechanics::Quantities::mass::mass";
                        unitRef = "ISO-80000.mdzip#_18_0beta_903028d_1388650182449_927337_80210";
                        unitName = "ISO-80000::ISO80000-4 Mechanics::Units::gram::milligram";
                    }
                }
                attribute def 'mass[kilogram]' :> 'ISO-80000'::'ISO80000-4 Mechanics'::'Quantities'::'mass'::'mass' {
                    @CSRMv1Metadata::ValueTypeSource {
                        sourceRef = "ISO-80000.mdzip#_18_0beta_903028d_1388650184728_204346_92547";
                        quantityKindRef = "ISO-80000.mdzip#_18_0beta_903028d_1388650182002_641636_78041";
                        quantityKindName = "ISO-80000::ISO80000-4 Mechanics::Quantities::mass::mass";
                        unitRef = "ISO-80000.mdzip#_18_0beta_903028d_1388650200893_965853_182246";
                        unitName = "ISO-80000::ISO80000-4 Mechanics::Units::gram::kilogram";
                    }
                }
                attribute def 'mass' {
                    @CSRMv1Metadata::ValueTypeSource {
                        sourceRef = "ISO-80000.mdzip#_18_0beta_903028d_1388650193270_151662_136538";
                        quantityKindRef = "ISO-80000.mdzip#_18_0beta_903028d_1388650182002_641636_78041";
                        quantityKindName = "ISO-80000::ISO80000-4 Mechanics::Quantities::mass::mass";
                        unitRef = "";
                        unitName = "";
                    }
                }
                attribute def 'mass[gram]' :> 'ISO-80000'::'ISO80000-4 Mechanics'::'Quantities'::'mass'::'mass' {
                    @CSRMv1Metadata::ValueTypeSource {
                        sourceRef = "ISO-80000.mdzip#_18_0beta_903028d_1388650202383_273056_185530";
                        quantityKindRef = "ISO-80000.mdzip#_18_0beta_903028d_1388650182002_641636_78041";
                        quantityKindName = "ISO-80000::ISO80000-4 Mechanics::Quantities::mass::mass";
                        unitRef = "ISO-80000.mdzip#_18_0beta_903028d_1388650180832_249784_70387";
                        unitName = "ISO-80000::ISO80000-4 Mechanics::Units::gram::gram";
                    }
                }
            }
        }
    }
    package 'ISO80000-9 Physical Chemestry and Molecular Physics' {
        package 'Quantities' {
            package 'amount of substance concentration' {
                attribute def 'amount of substance concentration[mole per cubic metre]' :> 'ISO-80000'::'ISO80000-9 Physical Chemestry and Molecular Physics'::'Quantities'::'amount of substance concentration'::'amount of substance concentration' {
                    @CSRMv1Metadata::ValueTypeSource {
                        sourceRef = "ISO-80000.mdzip#_18_0beta_903028d_1388650181014_906619_71386";
                        quantityKindRef = "ISO-80000.mdzip#_18_0beta_903028d_1388650195383_351988_148708";
                        quantityKindName = "ISO-80000::ISO80000-9 Physical Chemestry and Molecular Physics::Quantities::amount of substance concentration::amount of substance concentration";
                        unitRef = "ISO-80000.mdzip#_18_0beta_903028d_1388650196386_484281_155232";
                        unitName = "ISO-80000::ISO80000-9 Physical Chemestry and Molecular Physics::Units::mole per cubic metre::mole per cubic metre";
                    }
                }
                attribute def 'amount of substance concentration' {
                    @CSRMv1Metadata::ValueTypeSource {
                        sourceRef = "ISO-80000.mdzip#_18_0beta_903028d_1388650195952_388056_152400";
                        quantityKindRef = "ISO-80000.mdzip#_18_0beta_903028d_1388650195383_351988_148708";
                        quantityKindName = "ISO-80000::ISO80000-9 Physical Chemestry and Molecular Physics::Quantities::amount of substance concentration::amount of substance concentration";
                        unitRef = "";
                        unitName = "";
                    }
                }
            }
            package 'amount of substance' {
                attribute def 'amount of substance[mole]' :> 'ISO-80000'::'ISO80000-9 Physical Chemestry and Molecular Physics'::'Quantities'::'amount of substance'::'amount of substance' {
                    @CSRMv1Metadata::ValueTypeSource {
                        sourceRef = "ISO-80000.mdzip#_18_0beta_903028d_1388650189229_159383_113368";
                        quantityKindRef = "ISO-80000.mdzip#_18_0beta_903028d_1388650196429_792899_155549";
                        quantityKindName = "ISO-80000::ISO80000-9 Physical Chemestry and Molecular Physics::Quantities::amount of substance::amount of substance";
                        unitRef = "ISO-80000.mdzip#_18_0beta_903028d_1388650177247_951523_50211";
                        unitName = "ISO-80000::ISO80000-9 Physical Chemestry and Molecular Physics::Units::mole::mole";
                    }
                }
                attribute def 'amount of substance' {
                    @CSRMv1Metadata::ValueTypeSource {
                        sourceRef = "ISO-80000.mdzip#_18_0beta_903028d_1388650189782_109507_116243";
                        quantityKindRef = "ISO-80000.mdzip#_18_0beta_903028d_1388650196429_792899_155549";
                        quantityKindName = "ISO-80000::ISO80000-9 Physical Chemestry and Molecular Physics::Quantities::amount of substance::amount of substance";
                        unitRef = "";
                        unitName = "";
                    }
                }
            }
        }
    }
    package 'ISO80000-7 Light' {
        package 'Quantities' {
            package 'luminance' {
                attribute def 'luminance[candela per square metre]' :> 'ISO-80000'::'ISO80000-7 Light'::'Quantities'::'luminance'::'luminance' {
                    @CSRMv1Metadata::ValueTypeSource {
                        sourceRef = "ISO-80000.mdzip#_18_0beta_903028d_1388650191542_644508_126071";
                        quantityKindRef = "ISO-80000.mdzip#_18_0beta_903028d_1388650181861_135667_77116";
                        quantityKindName = "ISO-80000::ISO80000-7 Light::Quantities::luminance::luminance";
                        unitRef = "ISO-80000.mdzip#_18_0beta_903028d_1388650190123_334170_118298";
                        unitName = "ISO-80000::ISO80000-7 Light::Units::candela per square metre::candela per square metre";
                    }
                }
                attribute def 'luminance' {
                    @CSRMv1Metadata::ValueTypeSource {
                        sourceRef = "ISO-80000.mdzip#_18_0beta_903028d_1388650192131_861488_130374";
                        quantityKindRef = "ISO-80000.mdzip#_18_0beta_903028d_1388650181861_135667_77116";
                        quantityKindName = "ISO-80000::ISO80000-7 Light::Quantities::luminance::luminance";
                        unitRef = "";
                        unitName = "";
                    }
                }
            }
            package 'luminous intensity' {
                attribute def 'luminous intensity' {
                    @CSRMv1Metadata::ValueTypeSource {
                        sourceRef = "ISO-80000.mdzip#_18_0beta_903028d_1388650192064_908818_130251";
                        quantityKindRef = "ISO-80000.mdzip#_18_0beta_903028d_1388650182376_395027_79567";
                        quantityKindName = "ISO-80000::ISO80000-7 Light::Quantities::luminous intensity::luminous intensity";
                        unitRef = "";
                        unitName = "";
                    }
                }
                attribute def 'luminous intensity[candela]' :> 'ISO-80000'::'ISO80000-7 Light'::'Quantities'::'luminous intensity'::'luminous intensity' {
                    @CSRMv1Metadata::ValueTypeSource {
                        sourceRef = "ISO-80000.mdzip#_18_0beta_903028d_1388650193761_648715_138929";
                        quantityKindRef = "ISO-80000.mdzip#_18_0beta_903028d_1388650182376_395027_79567";
                        quantityKindName = "ISO-80000::ISO80000-7 Light::Quantities::luminous intensity::luminous intensity";
                        unitRef = "ISO-80000.mdzip#_18_0beta_903028d_1388650184871_937401_93506";
                        unitName = "ISO-80000::ISO80000-7 Light::Units::candela::candela";
                    }
                }
            }
        }
    }
    package 'ISO80000-5 Thermodynamics' {
        package 'Quantities' {
            package 'thermodynamic temperature' {
                attribute def 'thermodynamic temperature[kelvin]' :> 'ISO-80000'::'ISO80000-5 Thermodynamics'::'Quantities'::'thermodynamic temperature'::'thermodynamic temperature' {
                    @CSRMv1Metadata::ValueTypeSource {
                        sourceRef = "ISO-80000.mdzip#_18_0beta_903028d_1388650193666_776688_138662";
                        quantityKindRef = "ISO-80000.mdzip#_18_0beta_903028d_1388650180164_41403_63705";
                        quantityKindName = "ISO-80000::ISO80000-5 Thermodynamics::Quantities::thermodynamic temperature::thermodynamic temperature";
                        unitRef = "ISO-80000.mdzip#_18_0beta_903028d_1388650196825_515764_157852";
                        unitName = "ISO-80000::ISO80000-5 Thermodynamics::Units::kelvin::kelvin";
                    }
                }
                attribute def 'thermodynamic temperature' {
                    @CSRMv1Metadata::ValueTypeSource {
                        sourceRef = "ISO-80000.mdzip#_18_0beta_903028d_1388650195097_84516_146909";
                        quantityKindRef = "ISO-80000.mdzip#_18_0beta_903028d_1388650180164_41403_63705";
                        quantityKindName = "ISO-80000::ISO80000-5 Thermodynamics::Quantities::thermodynamic temperature::thermodynamic temperature";
                        unitRef = "";
                        unitName = "";
                    }
                }
            }
        }
    }
}
