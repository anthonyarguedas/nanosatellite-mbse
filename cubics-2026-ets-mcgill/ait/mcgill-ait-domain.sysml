// Publicly documented institutional snapshot. Sources and caveats: README.md.
// Positions are published roles. Potential concerns and contacts are suggestions,
// not CUBICS assignments. Concern strings list topics, not confirmed commitments.
package McGillAITDomain {
    part def 'Jamil Ahram' {
        attribute position : ScalarValues::String = "Faculty Workshop manager";
        attribute potentialConcerns : ScalarValues::String = "workshop scheduling, machining";
        attribute potentialContact : ScalarValues::Boolean = true;
    }
    part def 'Meisam Aghajani' {
        attribute position : ScalarValues::String = "Chief shop technician";
        attribute potentialConcerns : ScalarValues::String = "prototype machining, part fit";
    }
    part def 'Sam Minter' {
        attribute position : ScalarValues::String = "Wong Machine Shop coordinator";
        attribute potentialConcerns : ScalarValues::String = "CNC fabrication, fixtures";
        attribute potentialContact : ScalarValues::Boolean = true;
    }
    part def 'Zhao Lu' {
        attribute position : ScalarValues::String = "Nanotools manager";
        attribute potentialConcerns : ScalarValues::String = "cleanroom access, process scheduling";
        attribute potentialContact : ScalarValues::Boolean = true;
    }
    part def 'John Li' {
        attribute position : ScalarValues::String = "Equipment technologist";
        attribute potentialConcerns : ScalarValues::String = "Nanotools equipment, microfab tests";
        attribute potentialContact : ScalarValues::Boolean = true;
    }
    part def 'Peng Yang' {
        attribute position : ScalarValues::String = "Research assistant";
        attribute potentialConcerns : ScalarValues::String = "microfabrication research support";
    }

    // MIAE lists these associated academic faculty across McGill departments.
    // Their publications and profiles support possible technical outreach topics.
    part def 'Inna Sharf' {
        attribute position : ScalarValues::String = "MIAE associated faculty, Mechanical Engineering";
        attribute potentialConcerns : ScalarValues::String = "spacecraft attitude dynamics, CubeSat servicer control";
        attribute potentialContact : ScalarValues::Boolean = true;
    }
    part def 'James Richards Forbes' {
        attribute position : ScalarValues::String = "MIAE associated faculty, Mechanical Engineering";
        attribute potentialConcerns : ScalarValues::String = "aerospace navigation, guidance and control, state estimation";
        attribute potentialContact : ScalarValues::Boolean = true;
    }
    part def 'Pascal Hubert' {
        attribute position : ScalarValues::String = "MIAE associated faculty, Mechanical Engineering";
        attribute potentialConcerns : ScalarValues::String = "aerospace structures, composite materials";
        attribute potentialContact : ScalarValues::Boolean = true;
    }
    part def 'Harry Leib' {
        attribute position : ScalarValues::String = "MIAE associated faculty, Electrical and Computer Engineering";
        attribute potentialConcerns : ScalarValues::String = "communication systems, coding and signal processing";
        attribute potentialContact : ScalarValues::Boolean = true;
    }
    part def 'Andrew Higgins' {
        attribute position : ScalarValues::String = "MIAE associated faculty, Mechanical Engineering";
        attribute potentialConcerns : ScalarValues::String = "laser thermal propulsion research, lightsail stability";
        attribute potentialContact : ScalarValues::Boolean = true;
    }

    // The McGill Rocket Team publishes these club roles on its About Us roster.
    part def 'Natalie Hassanien' {
        attribute position : ScalarValues::String = "Captain";
        attribute potentialConcerns : ScalarValues::String = "club coordination, student continuity";
        attribute potentialContact : ScalarValues::Boolean = true;
    }
    part def 'Saiid Haymour' {
        attribute position : ScalarValues::String = "Captain";
        attribute potentialConcerns : ScalarValues::String = "club coordination, student continuity";
        attribute potentialContact : ScalarValues::Boolean = true;
    }
    part def 'Rawan Olabi' {
        attribute position : ScalarValues::String = "Captain";
        attribute potentialConcerns : ScalarValues::String = "club coordination, student continuity";
        attribute potentialContact : ScalarValues::Boolean = true;
    }
    part def 'Abdel Elbarkouky' {
        attribute position : ScalarValues::String = "Orbital CubeSat Director";
        attribute potentialConcerns : ScalarValues::String = "CubeSat integration, student work";
        attribute potentialContact : ScalarValues::Boolean = true;
    }
    part def 'Rose Storozuk' {
        attribute position : ScalarValues::String = "Orbital CubeSat Director";
        attribute potentialConcerns : ScalarValues::String = "CubeSat integration, student work";
        attribute potentialContact : ScalarValues::Boolean = true;
    }
    part def 'Ben Waterman Holmes' {
        attribute position : ScalarValues::String = "Quality Control Technical Director";
        attribute potentialConcerns : ScalarValues::String = "inspection, test records";
        attribute potentialContact : ScalarValues::Boolean = true;
    }
    part def 'Youssef Mustafa' {
        attribute position : ScalarValues::String = "Workshop Manager";
        attribute potentialConcerns : ScalarValues::String = "club workshop, prototype work";
        attribute potentialContact : ScalarValues::Boolean = true;
    }
    part def 'Pierre Arbaji' {
        attribute position : ScalarValues::String = "Design & Optimization Advisor";
        attribute potentialConcerns : ScalarValues::String = "design review, optimization";
        attribute potentialContact : ScalarValues::Boolean = true;
    }
    part def 'Maxim Żmudziński' {
        attribute position : ScalarValues::String = "Electrical Technical Director";
        attribute potentialConcerns : ScalarValues::String = "electrical integration, bench tests";
        attribute potentialContact : ScalarValues::Boolean = true;
    }
    part def 'Majd Boulos' {
        attribute position : ScalarValues::String = "Mechanical Technical Director";
        attribute potentialConcerns : ScalarValues::String = "mechanical integration, fit tests";
        attribute potentialContact : ScalarValues::Boolean = true;
    }
    part def 'Luca Chamoun' {
        attribute position : ScalarValues::String = "VP Finance";
        attribute potentialConcerns : ScalarValues::String = "club budget, procurement";
        attribute potentialContact : ScalarValues::Boolean = true;
    }
    part def 'Eliott Dantuono' {
        attribute position : ScalarValues::String = "VP Media";
        attribute potentialConcerns : ScalarValues::String = "club outreach, public communication";
        attribute potentialContact : ScalarValues::Boolean = true;
    }
    part def 'Sarah Mbazaa' {
        attribute position : ScalarValues::String = "VP Media";
        attribute potentialConcerns : ScalarValues::String = "club outreach, public communication";
        attribute potentialContact : ScalarValues::Boolean = true;
    }

    // Named leads and team titles on the club's published roster.
    part def 'Maël Cipréos' {
        attribute position : ScalarValues::String = "Aerostructures Lead";
        attribute potentialConcerns : ScalarValues::String = "structures, fit checks";
        attribute potentialContact : ScalarValues::Boolean = true;
    }
    part def 'Bianca Daskalov' {
        attribute position : ScalarValues::String = "Aerostructures Lead";
        attribute potentialConcerns : ScalarValues::String = "structures, fit checks";
        attribute potentialContact : ScalarValues::Boolean = true;
    }
    part def 'Greg Shtychno' {
        attribute position : ScalarValues::String = "Aerostructures Lead";
        attribute potentialConcerns : ScalarValues::String = "structures, fit checks";
        attribute potentialContact : ScalarValues::Boolean = true;
    }
    part def 'Léo Mindlin' {
        attribute position : ScalarValues::String = "Avionics Lead";
        attribute potentialConcerns : ScalarValues::String = "electronics, telemetry tests";
        attribute potentialContact : ScalarValues::Boolean = true;
    }
    part def 'Carolyn Wu' {
        attribute position : ScalarValues::String = "Avionics Lead";
        attribute potentialConcerns : ScalarValues::String = "electronics, telemetry tests";
        attribute potentialContact : ScalarValues::Boolean = true;
    }
    part def 'Henrique Moreira' {
        attribute position : ScalarValues::String = "Launch Systems Lead";
        attribute potentialConcerns : ScalarValues::String = "launch operations, ground safety";
        attribute potentialContact : ScalarValues::Boolean = true;
    }
    part def 'Diwen Pollet-Villard--Su' {
        attribute position : ScalarValues::String = "Launch Systems Lead";
        attribute potentialConcerns : ScalarValues::String = "launch operations, ground safety";
        attribute potentialContact : ScalarValues::Boolean = true;
    }
    part def 'Alexandra Stroeder' {
        attribute position : ScalarValues::String = "Launch Systems Lead";
        attribute potentialConcerns : ScalarValues::String = "launch operations, ground safety";
        attribute potentialContact : ScalarValues::Boolean = true;
    }
    part def 'Ashlyn Bourgeois' {
        attribute position : ScalarValues::String = "Payload Lead";
        attribute potentialConcerns : ScalarValues::String = "payload integration, instrument tests";
        attribute potentialContact : ScalarValues::Boolean = true;
    }
    part def 'Lily White' {
        attribute position : ScalarValues::String = "Payload Lead";
        attribute potentialConcerns : ScalarValues::String = "payload integration, instrument tests";
        attribute potentialContact : ScalarValues::Boolean = true;
    }
    part def 'Logan Acott' {
        attribute position : ScalarValues::String = "Propulsion Lead";
        attribute potentialConcerns : ScalarValues::String = "rocket propulsion, safety tests";
        attribute potentialContact : ScalarValues::Boolean = true;
    }
    part def 'Athanasios Mavrakanas' {
        attribute position : ScalarValues::String = "Propulsion Lead";
        attribute potentialConcerns : ScalarValues::String = "rocket propulsion, safety tests";
        attribute potentialContact : ScalarValues::Boolean = true;
    }
    part def 'Max Finch' {
        attribute position : ScalarValues::String = "Recovery Lead";
        attribute potentialConcerns : ScalarValues::String = "flight recovery, field tests";
        attribute potentialContact : ScalarValues::Boolean = true;
    }
    part def 'Sofia Del Raso' {
        attribute position : ScalarValues::String = "Recovery Lead";
        attribute potentialConcerns : ScalarValues::String = "flight recovery, field tests";
        attribute potentialContact : ScalarValues::Boolean = true;
    }

    // Faculty of Engineering Workshop site and staff page.
    part def 'Faculty Engineering Workshop' {
        ref part manager : 'Jamil Ahram';
        ref part 'chief shop technician' : 'Meisam Aghajani';
        part wongShop : 'Wong Machine Shop';
        part listedEquipment : 'Workshop Listed Equipment';
    }
    part def 'Wong Machine Shop' {
        ref part coordinator : 'Sam Minter';
    }
    part def 'Workshop Listed Equipment' {
        part cnc : 'CNC Mills and Lathes';
        part cmm : 'Coordinate Measuring Machine';
        part laser : 'Laser Cutter';
    }
    part def 'CNC Mills and Lathes';
    part def 'Coordinate Measuring Machine';
    part def 'Laser Cutter';

    // Nanotools' published staff, address, facility description and capabilities.
    part def 'Nanotools Microfab' {
        ref part manager : 'Zhao Lu';
        ref part 'equipment technologist' : 'John Li';
        ref part 'research assistant' : 'Peng Yang';
        ref part location : 'Rutherford Physics Building B1';
        part listedEquipment : 'Nanotools Listed Equipment';
    }
    part def 'Rutherford Physics Building B1';
    part def 'Nanotools Listed Equipment' {
        part cleanrooms : 'ISO 5 and ISO 6 Cleanrooms';
        part lithography : 'Lithography Tools';
        part deposition : 'Thin Film Deposition Tools';
        part etching : 'Etching Tools';
    }
    part def 'ISO 5 and ISO 6 Cleanrooms';
    part def 'Lithography Tools';
    part def 'Thin Film Deposition Tools';
    part def 'Etching Tools';

    // OCS1-OCS6 are projects listed under the club's Orbital CubeSat Division.
    // OCS6 reports two balloon flights in its last design cycle, not flight qualification.
    part def 'McGill Rocket Team' {
        ref part captain1 : 'Natalie Hassanien';
        ref part captain2 : 'Saiid Haymour';
        ref part captain3 : 'Rawan Olabi';
        ref part qualityDirector : 'Ben Waterman Holmes';
        ref part workshopManager : 'Youssef Mustafa';
        ref part designAdvisor : 'Pierre Arbaji';
        ref part electricalDirector : 'Maxim Żmudziński';
        ref part mechanicalDirector : 'Majd Boulos';
        part administration : 'MRT Administration';
        part orbitalCubeSat : 'Orbital CubeSat Division';
        part rocketSubteams : 'MRT Rocket Subteams';
    }
    part def 'MRT Administration' {
        ref part finance : 'Luca Chamoun';
        ref part media1 : 'Eliott Dantuono';
        ref part media2 : 'Sarah Mbazaa';
    }
    part def 'Orbital CubeSat Division' {
        ref part director1 : 'Abdel Elbarkouky';
        ref part director2 : 'Rose Storozuk';
        part ocs1 : 'OCS1 Structures and Mechanisms';
        part ocs2 : 'OCS2 Command and Data Handling';
        part ocs3 : 'OCS3 Space Ground Communications';
        part ocs4 : 'OCS4 Attitude Control';
        part ocs5 : 'OCS5 Power';
        part ocs6 : 'OCS6 High Altitude Balloon';
    }
    part def 'OCS1 Structures and Mechanisms';
    part def 'OCS2 Command and Data Handling';
    part def 'OCS3 Space Ground Communications';
    part def 'OCS4 Attitude Control';
    part def 'OCS5 Power';
    part def 'OCS6 High Altitude Balloon' {
        attribute reportedFlightsInLastCycle : ScalarValues::Integer = 2;
    }

    // These six rocket subteams are separate from the Orbital CubeSat Division.
    part def 'MRT Rocket Subteams' {
        part aerostructures : 'Rocket Aerostructures Team';
        part avionics : 'Rocket Avionics Team';
        part launchSystems : 'Rocket Launch Systems Team';
        part payload : 'Rocket Payload Team';
        part propulsion : 'Rocket Propulsion Team';
        part recovery : 'Rocket Recovery Team';
    }
    part def 'Rocket Aerostructures Team' {
        ref part lead1 : 'Maël Cipréos';
        ref part lead2 : 'Bianca Daskalov';
        ref part lead3 : 'Greg Shtychno';
    }
    part def 'Rocket Avionics Team' {
        ref part lead1 : 'Léo Mindlin';
        ref part lead2 : 'Carolyn Wu';
    }
    part def 'Rocket Launch Systems Team' {
        ref part lead1 : 'Henrique Moreira';
        ref part lead2 : 'Diwen Pollet-Villard--Su';
        ref part lead3 : 'Alexandra Stroeder';
    }
    part def 'Rocket Payload Team' {
        ref part lead1 : 'Ashlyn Bourgeois';
        ref part lead2 : 'Lily White';
    }
    part def 'Rocket Propulsion Team' {
        ref part lead1 : 'Logan Acott';
        ref part lead2 : 'Athanasios Mavrakanas';
    }
    part def 'Rocket Recovery Team' {
        ref part lead1 : 'Max Finch';
        ref part lead2 : 'Sofia Del Raso';
    }

    part def 'MIAE Associated Faculty' {
        ref part 'space robotics and attitude' : 'Inna Sharf';
        ref part 'navigation and control' : 'James Richards Forbes';
        ref part 'aerospace structures' : 'Pascal Hubert';
        ref part communications : 'Harry Leib';
        ref part 'propulsion research' : 'Andrew Higgins';
    }

    part def 'McGill AIT Faculty Domain' {
        part workshop : 'Faculty Engineering Workshop';
        part nanotools : 'Nanotools Microfab';
        part aerospace : 'MIAE Associated Faculty';
    }
}
