// INCOSE SSWG and OMG SDTF, CubeSat System Reference Model, CC BY 4.0.
// Direct source: ObjectManagementGroup/CSRM, Distro/CSRM XMI/CSRM.xmi.
// Generated by transcribe.py from the pinned vendor-neutral XMI. See README.md.
// Load with CSRMProfile.sysml in the same model project.
package OfficialCSRM {
    doc /* SysML v2 transcription of the official CSRM XMI model. The CSRM Profile is a distinct SysML v1 specification. */
    package 'Data' {
        doc /* Source XMI: eee_1045467100313_135436_1
        Comment PROJECT-646cdbb5-bf44-4c4e-8464-55757d072991_18_0_6_3e4019a_1472150965280_121218_12270
        Author:Rose.
        Created:8/25/16 2:49 PM.
        Title:.
        Comment:.
        UML kind: uml:Model
        Source-only uml:ProfileApplication _18_0_6_3e4019a_1472150965277_567258_12269: {"type": "uml:ProfileApplication", "id": "_18_0_6_3e4019a_1472150965277_567258_12269"} */
        package '01 - CubeSat System Reference Model' {
            doc /* Source XMI: _18_0_6_3e4019a_1472151505478_730469_12299
            Comment _19_0_3_2b0010b_1619897478239_980936_70532 (Explanation)
            This package contains the CSRM core. Additoinally, there are links to the examples and illustrations. You are free to use the elements or delete them if they do not apply to your design.
            Comment _19_0_3_2b0010b_1619897531064_593205_70559 (Explanation)
            This package contains CSRM examples and illustrations. This is provided to aid in development and to explain how to use the CSRM.
            Be careful to not use the elements in this package as part of your design. We suggest copying any element to the primary model.
            This section should be removed when not required for reference.
            UML kind: uml:Package */
            package '1 - Stakeholders' {
                doc /* Source XMI: _18_0_6_3e4019a_1472151507121_296228_12349
                Comment _18_4_1_3880181_1494685327661_292254_51026
                Stakeholders are any entities that have an interest or role in the system such as regulatory agencies, the deployer system, and mission system development and operations personnel.  Representative stakeholders are included in the model and can be extended as appropriate.
                There can be a number of stakeholders with varying interests.  Mission needs, objectives, constraints, and Rqts result from review, assessment, and integration of the varied interests.
                Comment _19_0_3_2b0010b_1619209166835_618099_2322 (HowTo)
                Double-click on on the individual Regulatory Agency Stakeholders to navigate to the stakeholder web sites
                Comment _19_0_3_2b0010b_1619209166835_732067_2333 (HowTo)
                Double-click on the stakeholder packages to navigate to the individual stakeholders.
                Comment _19_0_3_2b0010b_1619209166835_759559_2344 (Explanation)
                A stakeholder is any entity that has an interest in the system. Some are interested in the models themselves and others are interested in the missions that can be realized from the mission-specific instantiations of the model, and some have interests in both.
                Comment _19_0_3_2b0010b_1619209166850_845595_2355 (Explanation)
                There are two modeling efforts. One is the SSWG developing a CubeSat Reference Model with its logical architecture. The other is a team eventually taking the CubeSat Reference Model as a basis for its mission-specific logical and physical architectures.
                Comment _19_0_2_3880181_1637431073670_854193_55314 (Explanation)
                Stakeholders
                UML kind: uml:Package */
                package '1.1 Regulatory Agency Stakeholders' {
                    doc /* Source XMI: _18_0_6_3e4019a_1472151555147_792733_13596
                    Comment _19_0_2_3880181_1600788576667_236770_63294
                    CubeSat projects are pursued internationally, but the licenses and regulations that cover their activities are administered at the national level. The timelines and procedures for requesting and receiving approval must be well understood and part of the model.
                    Comment _19_0_3_2b0010b_1619206846073_966237_942 (Explanation)
                    CubeSat projects are pursued internationally, but the licenses and regulations that cover their activities are administered at the national level. The timelines and procedures for requesting and receiving approval must be well understood and part of the model.
                    Comment _19_0_3_2b0010b_1619206846073_430884_964 (Explanation)
                    A double click on these elements links to the web sites
                    Comment _19_0_3_2b0010b_1619206846073_789781_975 (Explanation)
                    A mission specific team will add  Regulatory Agencies as applicable
                    Comment _19_0_3_2b0010b_1619206879285_77215_994 (HowTo)
                    Double-click on a table and add and delete elements as needed.
                    Click on Add New to add a new element  to the containment tree and to the table.
                    Right click the new element in the table then left click Select in Containment Tree to navigate to the new element.
                    Select an element and click on Delete to delete from the element table and the Containment Tree.
                    Comment _19_0_2_3880181_1637184808148_441176_55562 (Explanation)
                    Regulatory Agency Stakeholders and Concerns - Population
                    UML kind: uml:Package */
                    package '1.1.2 - Regulatory Agency Stakeholders Concerns' {
                        doc /* Source XMI: _18_5_1_3880181_1506380737786_207669_58890
                        Comment _19_0_2_3880181_1600790371807_305503_63298
                        A mission specific team will add Regulatory Agencies stakeholder concerns as applicable
                        UML kind: uml:Package */
                        part def 'Regulatory Agency Stakeholder Concerns' {
                            @OfficialCSRMProfile::'Concerns and Requirements Profile'::'Group';
                            doc /* Source XMI: _18_5_2_3880181_1525198676331_873364_67531
                            Stereotype Group: Text=This Group provides the prefix and numbering scheme., Id=RegAgcyCons_1
                            UML kind: uml:Class */
                            part def 'Regulatory Agency Stakeholder Concern Name' {
                                @OfficialCSRMProfile::'Concerns and Requirements Profile'::'StakeholderConcern';
                                doc /* Source XMI: _18_5_2_3880181_1525198758463_808009_67537
                                Stereotype StakeholderConcern: Text=, Id=RegAgcyCons_1.1
                                UML kind: uml:Class */
                            }
                        }
                    }
                    package '1.1.1 - Regulatory Agency Stakeholders' {
                        doc /* Source XMI: _19_0_2_3880181_1576702969357_143852_63074
                        Comment _19_0_2_3880181_1600788762355_794413_63295
                        A mission specific team will add Regulatory Agencies stakeholders as applicable.
                        UML kind: uml:Package */
                        part def 'Regulatory Agency Name ' {
                            @OfficialCSRMProfile::'Architecture Structures Profile'::'Stakeholder';
                            doc /* Source XMI: _19_0_2_3880181_1636478056877_711014_56404
                            Stereotype Stakeholder
                            UML kind: uml:Class */
                        }
                    }
                }
                package '1.3 CubeSat Deployer Systems' {
                    doc /* Source XMI: _18_5_2_3880181_1542045188056_448463_62419
                    Comment _19_0_2_3880181_1600867044193_6344_63295
                    The design and development of the mission specific CubeSat must satisfy the Rqts for interfacing with a CubeSat Deployer.
                    UML kind: uml:Package */
                }
                package '1.2 Mission Stakeholders' {
                    doc /* Source XMI: _19_0_3_2b0010b_1619455282477_750087_10270
                    Comment _19_0_2_3880181_1636643780928_374543_56375 (Explanation)
                    Mission Constraint - A limitation placed on cost, schedule, or implementation techniques
                    Comment _19_0_2_3880181_1636644094059_285197_56413 (Explanation)
                    Mission Need - A concise description of a need or service that the system must provide.
                    Comment _19_0_2_3880181_1636644094059_130443_56414 (Explanation)
                    Mission Objective - A broad set of goals that must be achieved in order to successfully satisfy the stated mission need,
                    Comment _19_0_2_3880181_1636645107840_952779_56613 (Explanation)
                    Mission Requirement - Statements of fact and assumptions that define the expectations of the system in terms of mission objectives, environment, constraints, and measures of effectiveness
                    Comment _19_0_2_3880181_1636645617432_604977_56683 (Explanation)
                    Stakeholder Concern -  Interest in a system relevant to one or more of its stakeholders.
                    Comment _19_0_2_3880181_1636646203391_486135_56763 (Explanation)
                    Mission Stakeholders -Those with an interest in the mission-specific CubeSat  space and ground system.
                    Comment _19_0_2_3880181_1636647014690_23272_57298 (HowTo)
                    Double-click on a table and add and delete elements as needed.
                    Click on Add New to add a new element  to the containment tree and to the table.
                    Right click the new element in the table then left click Select in Containment Tree to navigate to the new element.
                    Select an element and click on Delete to delete from the element table and the Containment Tree.
                    Comment _19_0_2_3880181_1637186331719_238161_55767 (Explanation)
                    Mission Stakeholders and Requirements - Population
                    Comment _19_0_2_3880181_1637431577134_166593_55506 (Explanation)
                    Mission Stakeholders
                    UML kind: uml:Package */
                    package '1.2.1 - Mission Stakeholders' {
                        doc /* Source XMI: _19_0_3_2b0010b_1619453686993_218164_8481
                        UML kind: uml:Package */
                        part def 'Mission Stakeholder A' {
                            @OfficialCSRMProfile::'Architecture Structures Profile'::'Stakeholder';
                            doc /* Source XMI: _19_0_2_3880181_1636494199134_213802_57109
                            Stereotype Stakeholder
                            Comment _19_0_2_3880181_1637432890965_120187_55644
                            Description
                            UML kind: uml:Class */
                        }
                        part def 'Mission Stakeholder B' {
                            @OfficialCSRMProfile::'Architecture Structures Profile'::'Stakeholder';
                            doc /* Source XMI: _19_0_2_3880181_1637432691948_576398_55641
                            Stereotype Stakeholder
                            Comment _19_0_2_3880181_1637432904567_684686_55645
                            Description
                            UML kind: uml:Class */
                        }
                    }
                    package '1.2.3 - Mission Needs' {
                        doc /* Source XMI: _19_0_3_2b0010b_1619453816825_519527_8531
                        UML kind: uml:Package */
                        part def 'Mission Needs Group' {
                            @OfficialCSRMProfile::'Concerns and Requirements Profile'::'Group';
                            doc /* Source XMI: _18_5_2_3880181_1508806905962_791714_64301
                            Stereotype Group: Text=The Group provides the prefix and numbering scheme which is easy to change., Id=MN_1
                            UML kind: uml:Class */
                            part def 'Mission Need Name' {
                                @OfficialCSRMProfile::'Concerns and Requirements Profile'::'MissionNeed';
                                doc /* Source XMI: _18_5_2_3880181_1522968190273_241604_65491
                                Stereotype MissionNeed: Text=Statement of need, Id=MN_1.1
                                UML kind: uml:Class */
                            }
                        }
                    }
                    package '1.2.5 - Mission Constraints' {
                        doc /* Source XMI: _19_0_3_2b0010b_1619453866499_556928_8551
                        UML kind: uml:Package */
                        part def 'Mission Constraints Group' {
                            @OfficialCSRMProfile::'Concerns and Requirements Profile'::'Group';
                            doc /* Source XMI: _18_5_2_3880181_1508807175129_570655_64331
                            Stereotype Group: Text=The Group provides the prefix and numbering scheme which is easy to change., Id=MC_1
                            UML kind: uml:Class */
                            part def 'Mission Constraint Name' {
                                @OfficialCSRMProfile::'Concerns and Requirements Profile'::'MissionConstraint';
                                doc /* Source XMI: _18_5_2_3880181_1523563430558_500151_69688
                                Stereotype MissionConstraint: Text=Statement of constraint, Id=MC_1.1
                                UML kind: uml:Class */
                            }
                        }
                    }
                    package '1.2.6 - Mission Rqts' {
                        doc /* Source XMI: _19_0_3_2b0010b_1619453962740_119572_8573
                        UML kind: uml:Package */
                        part def 'Mission Rqts Group' {
                            @OfficialCSRMProfile::'Concerns and Requirements Profile'::'Group';
                            doc /* Source XMI: _18_5_2_3880181_1508807702110_741184_64518
                            Stereotype Group: Text=The Group provides the prefix and numbering scheme which is easy to change., Id=MR_1
                            UML kind: uml:Class */
                            requirement def 'Requirement Name' {
                                @OfficialCSRMProfile::'Concerns and Requirements Profile'::'MissionRequirement';
                                doc /* Shall statement */
                                comment /* Source XMI: _19_0_2_3880181_1572554664590_968521_63061
                                Stereotype MissionRequirement: Text=Shall statement, Id=MR_1.1
                                UML kind: uml:Class */
                            }
                        }
                    }
                    package '1.2.4 - Mission Objectives' {
                        doc /* Source XMI: _19_0_3_2b0010b_1619453836877_16079_8540
                        UML kind: uml:Package */
                        part def 'Mission Objectives Group' {
                            @OfficialCSRMProfile::'Concerns and Requirements Profile'::'Group';
                            doc /* Source XMI: _18_5_2_3880181_1508807015552_77281_64310
                            Stereotype Group: Text=The Group provides the prefix and numbering scheme which is easy to change., Id=MO_1
                            UML kind: uml:Class */
                            part def 'Mission Objective Name' {
                                @OfficialCSRMProfile::'Concerns and Requirements Profile'::'MissionObjective';
                                doc /* Source XMI: _18_5_2_3880181_1523563721181_692079_69816
                                Stereotype MissionObjective: Text=Statement of Objective, Id=MO_1.1
                                UML kind: uml:Class */
                            }
                        }
                    }
                    package '1.2.2 - Mission Stakeholder Concerns' {
                        doc /* Source XMI: _19_0_3_2b0010b_1619453798316_711098_8522
                        UML kind: uml:Package */
                        part def 'Mission Stakeholder Concerns' {
                            @OfficialCSRMProfile::'Concerns and Requirements Profile'::'Group';
                            doc /* Source XMI: _18_5_2_3880181_1508806698158_449734_64280
                            Stereotype Group: Text=The Group provides the prefix and numbering scheme which is easy to change., Id=SC_1
                            UML kind: uml:Class */
                            part def 'Mission Stakeholder A Concern 1' {
                                @OfficialCSRMProfile::'Concerns and Requirements Profile'::'StakeholderConcern';
                                doc /* Source XMI: _18_5_2_3880181_1523562363679_812596_69490
                                Stereotype StakeholderConcern: Text=Statement of concern, Id=SC_1.1
                                UML kind: uml:Class */
                            }
                        }
                        dependency relationship_1 from OfficialCSRM::'Data'::'01 - CubeSat System Reference Model'::'1 - Stakeholders'::'1.2 Mission Stakeholders'::'1.2.2 - Mission Stakeholder Concerns'::'Mission Stakeholder Concerns'::'Mission Stakeholder A Concern 1' to OfficialCSRM::'Data'::'01 - CubeSat System Reference Model'::'1 - Stakeholders'::'1.2 Mission Stakeholders'::'1.2.1 - Mission Stakeholders'::'Mission Stakeholder A' {
                            doc /* Source XMI: _19_0_2_3880181_1637433099150_515220_55704
                            Stereotype Trace
                            UML kind: uml:Abstraction */
                        }
                        dependency relationship_2 from OfficialCSRM::'Data'::'01 - CubeSat System Reference Model'::'1 - Stakeholders'::'1.2 Mission Stakeholders'::'1.2.2 - Mission Stakeholder Concerns'::'Mission Stakeholder Concerns'::'Mission Stakeholder A Concern 1' to OfficialCSRM::'Data'::'01 - CubeSat System Reference Model'::'1 - Stakeholders'::'1.2 Mission Stakeholders'::'1.2.6 - Mission Rqts'::'Mission Rqts Group'::'Requirement Name' {
                            doc /* Source XMI: _19_0_2_3880181_1637504864605_958298_55607
                            Stereotype Trace
                            UML kind: uml:Abstraction */
                        }
                    }
                }
            }
            package '5 - Architecture' {
                doc /* Source XMI: _18_4_1_3880181_1493412059102_856179_46900
                Comment _19_0_2_3880181_1600786453058_849185_62885
                The CSRM provides a CubeSat logical architecture. The logical components are abstractions of the physical components that perform the system functionality without imposing implementation constraints.
                The physical architecture defines physical components of the system including hardware, software, persistent data, and operational procedures.
                The CSRM logical elements are a starting point for a mission-specific CubeSat logical architecture, followed by the physical architecture and the CubeSat development.
                The architecture hierarchy starts at the CubeSat Domain and CubeSat Enterprise which consists of the CubeSat space segment and Ground segment.
                The CubeSat and Ground subsystems are generically and loosely defined as a starting point for the mission specific CubeSat team.
                The CubeSat team determines what subsystem capabilities are needed and whether they are provided by software, hardware, persistent data, or operator procedures.
                The Rqts and logical architecture hierarchies are parallel constructs.
                The subsystem architectures decompose to component architectures with notional example components.
                The mission-specific architecture team will replace these notional components with identified logical components which will be eventually be replaced with physical components.
                The enterprise, segment, and subsystem packages contain packages for behaviors, structures.
                Behaviors include use case, activity, sequence, and state diagrams.
                Structures include block definition diagrams and internal block definition diagrams.
                Comment _19_0_3_2b0010b_1619531887769_962801_13584 (Explanation)
                The CRM provides a CubeSat logical architecture. The logical components are abstractions of the physical components that perform the system functionality without imposing implementation constraints.
                The physical architecture defines physical components of the system including hardware, software, persistent data, and operational procedures.
                The CRM logical elements are a starting point for a mission-specific CubeSat logical architecture, followed by the physical architecture and the CubeSat development.
                The enterprise, segment, and subsystem packages contain packages for behaviors, structures.  Behaviors include use case, activity, sequence, and state diagrams. Structures include block definition diagrams and internal block definition diagrams.
                Comment _19_0_3_2b0010b_1619531887779_34599_13595 (HowTo)
                Double-click on the Domain, Enterprise, Segment, and Subsystem packages to navigate to their structure block definition diagrams.
                Comment _19_0_3_2b0010b_1619531887784_812476_13606 (Explanation)
                The CubeSat Component package contain representative components.  The mission-specific CubeSat team populates the CubeSat and Ground System Component packages with their mission-specific components.
                Comment _19_0_3_2b0010b_1619531887788_1285_13617 (Explanation)
                The CubeSat and Ground subsystems are broadly defined as a starting point for the mission-specific CubeSat team.
                The CubeSat team determines what subsystem capabilities are needed and whether they are provided by software, hardware, persistent data, or operator procedures
                Subsystems can be eliminated if not needed,e.g. Propulsion. Subsystems can be combined, e.g. Attitude Determination and Control subsystem and Guidance, Navigation, and Control.
                UML kind: uml:Package */
                package 'L0_Domain' {
                    doc /* Source XMI: _18_0_6_3e4019a_1472151507120_871537_12347
                    Comment _19_0_2_3880181_1600786849081_204021_62917
                    Domain represents the scope of the model.
                    The CubeSat Domain consists of the CubeSat Enterprise, Stakeholders, External Environment, and External Constraints.
                    External Environment consists of the Space Environment and Earth Environment. The External Constraints include such things as Licenses and Regulations.
                    UML kind: uml:Package */
                    part def 'CubeSat Reference Model Stakeholder' {
                        doc /* Source XMI: _18_0_6_3e4019a_1473981469179_690877_16298
                        Stereotype Stakeholder
                        Comment _18_0_6_3e4019a_1473981948075_946293_17392
                        Stakeholders for the CubeSat Reference Model are concerned with the proper development, management, and distribution of the reference model.
                        UML kind: uml:Actor */
                    }
                    package 'L0.1_Behaviors' {
                        doc /* Source XMI: _19_0_2_3880181_1561649452186_933431_61586
                        UML kind: uml:Package */
                    }
                    package 'L0.2_Structures' {
                        doc /* Source XMI: _19_0_2_3880181_1561649485859_620958_61587
                        UML kind: uml:Package */
                        part def 'CubeSat Domain' {
                            doc /* Source XMI: _19_0_2_3880181_1561649627280_727823_61644
                            Stereotype Block
                            UML kind: uml:Class */
                            part 'external Constraints' : OfficialCSRM::'Data'::'01 - CubeSat System Reference Model'::'5 - Architecture'::'L0_Domain'::'L0.2_Structures'::'External Constraints' {
                                doc /* Source XMI: _19_0_2_3880181_1561649969937_983270_61779
                                Stereotype PartProperty
                                UML aggregation: composite
                                UML association: _19_0_2_3880181_1561649969937_95066_61778 */
                            }
                            part 'external Environment' : OfficialCSRM::'Data'::'01 - CubeSat System Reference Model'::'5 - Architecture'::'L0_Domain'::'L0.2_Structures'::'External Environment' {
                                doc /* Source XMI: _19_0_2_3880181_1561649978061_109459_61795
                                Stereotype PartProperty
                                UML aggregation: composite
                                UML association: _19_0_2_3880181_1561649978061_298291_61794 */
                            }
                            part 'cubeSat Mission Enterprise' : OfficialCSRM::'Data'::'01 - CubeSat System Reference Model'::'5 - Architecture'::'L1_Enterprise'::'L1.2_Structures'::'CubeSat Mission Enterprise' {
                                doc /* Source XMI: _19_0_2_3880181_1561650281813_153110_61876
                                Stereotype PartProperty
                                UML aggregation: composite
                                UML association: _19_0_2_3880181_1561650281813_981425_61875 */
                            }
                        }
                        part def 'External Constraints' {
                            doc /* Source XMI: _19_0_2_3880181_1561649651952_344595_61646
                            Stereotype Block
                            UML kind: uml:Class */
                        }
                        part def 'External Environment' {
                            doc /* Source XMI: _19_0_2_3880181_1561649669768_504080_61648
                            Stereotype Block
                            UML kind: uml:Class */
                        }
                        connection def association_3 {
                            doc /* Source XMI: _19_0_2_3880181_1561649969937_95066_61778
                            UML end details are in the source map (SysML v2 connector ends have fixed [1..1] multiplicity). */
                            end end1 : OfficialCSRM::'Data'::'01 - CubeSat System Reference Model'::'5 - Architecture'::'L0_Domain'::'L0.2_Structures'::'External Constraints' {
                                doc /* Source XMI: _19_0_2_3880181_1561649969937_983270_61779
                                Stereotype PartProperty
                                UML end name: external Constraints */
                            }
                            end end2 : OfficialCSRM::'Data'::'01 - CubeSat System Reference Model'::'5 - Architecture'::'L0_Domain'::'L0.2_Structures'::'CubeSat Domain' {
                                doc /* Source XMI: _19_0_2_3880181_1561649969952_529102_61780
                                UML end name: (unnamed) */
                            }
                        }
                        connection def association_4 {
                            doc /* Source XMI: _19_0_2_3880181_1561649978061_298291_61794
                            UML end details are in the source map (SysML v2 connector ends have fixed [1..1] multiplicity). */
                            end end1 : OfficialCSRM::'Data'::'01 - CubeSat System Reference Model'::'5 - Architecture'::'L0_Domain'::'L0.2_Structures'::'External Environment' {
                                doc /* Source XMI: _19_0_2_3880181_1561649978061_109459_61795
                                Stereotype PartProperty
                                UML end name: external Environment */
                            }
                            end end2 : OfficialCSRM::'Data'::'01 - CubeSat System Reference Model'::'5 - Architecture'::'L0_Domain'::'L0.2_Structures'::'CubeSat Domain' {
                                doc /* Source XMI: _19_0_2_3880181_1561649978061_831384_61796
                                UML end name: (unnamed) */
                            }
                        }
                        connection def association_5 {
                            doc /* Source XMI: _19_0_2_3880181_1561650281813_981425_61875
                            UML end details are in the source map (SysML v2 connector ends have fixed [1..1] multiplicity). */
                            end end1 : OfficialCSRM::'Data'::'01 - CubeSat System Reference Model'::'5 - Architecture'::'L1_Enterprise'::'L1.2_Structures'::'CubeSat Mission Enterprise' {
                                doc /* Source XMI: _19_0_2_3880181_1561650281813_153110_61876
                                Stereotype PartProperty
                                UML end name: cubeSat Mission Enterprise */
                            }
                            end end2 : OfficialCSRM::'Data'::'01 - CubeSat System Reference Model'::'5 - Architecture'::'L0_Domain'::'L0.2_Structures'::'CubeSat Domain' {
                                doc /* Source XMI: _19_0_2_3880181_1561650281813_386148_61877
                                UML end name: (unnamed) */
                            }
                        }
                    }
                }
                package 'L4_Components' {
                    doc /* Source XMI: _18_4_1_3e4019a_1489768238372_67742_15719
                    Comment _19_0_2_3880181_1600787278706_61751_62950
                    Package of CubeSat subsystems components and of Ground systems components.
                    The subsystem architectures decompose to component architectures with notional example components.
                    The mission-specific architecture team will replace these notional components with identified logical components which will be eventually be replaced with physical components.
                    UML kind: uml:Package */
                    package 'L4.1_CubeSat Subsystems Components' {
                        doc /* Source XMI: _18_4_1_3e4019a_1489768275317_665796_15720
                        Comment _19_0_2_3880181_1600962659464_325847_62867
                        Package for CubeSat subsystems components.  To be populated by a mission specific team.
                        Comment _19_0_2_3880181_1637335264652_584101_56245 (Explanation)
                        CubeSat Components - Population
                        UML kind: uml:Package */
                        package 'L4.1.1_Mission Payload Components' {
                            doc /* Source XMI: _18_4_1_3e4019a_1489768307445_815725_15721
                            Comment _19_0_2_3880181_1600960867049_203990_62817
                            Package for CubeSat Mission Payload components.  To be populated by a mission specific team.
                            UML kind: uml:Package */
                            package 'L4.1.1.2_Structures' {
                                doc /* Source XMI: _18_4_1_3e4019a_1489768356542_210313_15722
                                Comment _19_0_3_2b0010b_1619902245492_114623_2960 (HowTo)
                                Select Components Table / Select in Containment Tree to locate Components pkg in the Containment tree
                                Open the Components Table
                                Select Add New to add a new component to the containment tree and to the table
                                Open the Subsystem bdd
                                Drag the new component element from the containment tree to the Subsystems bdd – to the Components pkg – to the Structure pkg
                                Right click the Subsystem block, select the directed composition relationship, and drag to the new component element
                                Return to the Component Population pkg.
                                Open the CubeSat Subsystems Structures Table to see the components associated with the Subsystem
                                UML kind: uml:Package */
                                part def 'Processor and Memory' {
                                    @OfficialCSRMProfile::'Architecture Structures Profile'::'Component';
                                    doc /* Source XMI: _18_4_1_3e4019a_1489768564386_78772_15756
                                    Stereotype Component
                                    UML kind: uml:Class */
                                    // UML generalization _18_4_1_3880181_1492191352174_160503_45879 to MD_customization_for_SysML.mdzip#_18_3_903028d_1448291312269_537593_13833
                                }
                                part def 'Instrument' {
                                    @OfficialCSRMProfile::'Architecture Structures Profile'::'Component';
                                    doc /* Source XMI: _18_4_1_3e4019a_1489768517309_104591_15754
                                    Stereotype Component
                                    UML kind: uml:Class */
                                    // UML generalization _18_4_1_3880181_1492191352173_216907_45878 to MD_customization_for_SysML.mdzip#_18_3_903028d_1448291312269_537593_13833
                                }
                            }
                            package 'L4.1.1.1_Behaviors' {
                                doc /* Source XMI: _19_0_2_3880181_1561133936889_53013_60487
                                UML kind: uml:Package */
                            }
                        }
                        package 'L4.1.2_Command and Data Handling Components' {
                            doc /* Source XMI: _18_4_1_3e4019a_1489768377503_913990_15723
                            Comment _19_0_2_3880181_1600961279863_129904_62818
                            Package for CubeSat Command and Data Handling components.  To be populated by a mission specific team.
                            UML kind: uml:Package */
                            package 'L4.1.2.2_Structures' {
                                doc /* Source XMI: _18_4_1_3e4019a_1489768377507_834291_15724
                                Comment _19_0_3_2b0010b_1619532033083_716258_13804 (HowTo)
                                Select Components Table / Select in Containment Tree to locate Components pkg in the Containment tree
                                Open the Components Table
                                Select Add New to add a new component to the containment tree and to the table
                                Open the Subsystem bdd
                                Drag the new component element from the containment tree to the Subsystems bdd – to the Components pkg – to the Structure pkg
                                Right click the Subsystem block, select the directed composition relationship, and drag to the new component element
                                Return to the Component Population pkg.
                                Open the CubeSat Subsystems Structures Table to see the components associated with the Subsystem
                                UML kind: uml:Package */
                                part def 'Processor and Memory' {
                                    @OfficialCSRMProfile::'Architecture Structures Profile'::'Component';
                                    doc /* Source XMI: _18_4_1_3e4019a_1489768596772_785377_15758
                                    Stereotype Component
                                    UML kind: uml:Class */
                                    // UML generalization _18_4_1_3880181_1492191352171_98636_45873 to MD_customization_for_SysML.mdzip#_18_3_903028d_1448291312269_537593_13833
                                }
                                part def 'Command, Telemetry, and Data Bus' {
                                    @OfficialCSRMProfile::'Architecture Structures Profile'::'Component';
                                    doc /* Source XMI: _18_4_1_3e4019a_1489768973777_796922_15784
                                    Stereotype Component
                                    UML kind: uml:Class */
                                    // UML generalization _18_4_1_3880181_1492191352171_47984_45874 to MD_customization_for_SysML.mdzip#_18_3_903028d_1448291312269_537593_13833
                                }
                            }
                            package 'L4.1.2.1_Behaviors' {
                                doc /* Source XMI: _19_0_2_3880181_1561134117840_94837_60489
                                UML kind: uml:Package */
                            }
                        }
                        package 'L4.1.3_Communication Components' {
                            doc /* Source XMI: _18_4_1_3e4019a_1489768485136_944524_15740
                            Comment _19_0_2_3880181_1600961337600_539374_62819
                            Package for CubeSat Communication components.  To be populated by a mission specific team.
                            UML kind: uml:Package */
                            package 'L4.1.3.2_Structures' {
                                doc /* Source XMI: _18_4_1_3e4019a_1489768485136_694220_15741
                                Comment _19_0_3_2b0010b_1619532064446_900576_13936 (HowTo)
                                Select Components Table / Select in Containment Tree to locate Components pkg in the Containment tree
                                Open the Components Table
                                Select Add New to add a new component to the containment tree and to the table
                                Open the Subsystem bdd
                                Drag the new component element from the containment tree to the Subsystems bdd – to the Components pkg – to the Structure pkg
                                Right click the Subsystem block, select the directed composition relationship, and drag to the new component element
                                Return to the Component Population pkg.
                                Open the CubeSat Subsystems Structures Table to see the components associated with the Subsystem
                                UML kind: uml:Package */
                                part def 'Processor and Memory' {
                                    @OfficialCSRMProfile::'Architecture Structures Profile'::'Component';
                                    doc /* Source XMI: _18_4_1_3e4019a_1489768598754_969812_15760
                                    Stereotype Component
                                    UML kind: uml:Class */
                                    // UML generalization _18_4_1_3880181_1492191352172_408878_45875 to MD_customization_for_SysML.mdzip#_18_3_903028d_1448291312269_537593_13833
                                }
                                part def 'Receive Antenna and Equipment' {
                                    @OfficialCSRMProfile::'Architecture Structures Profile'::'Component';
                                    doc /* Source XMI: _18_4_1_3e4019a_1489768796319_320639_15772
                                    Stereotype Component
                                    UML kind: uml:Class */
                                    // UML generalization _18_4_1_3880181_1492191352172_586969_45876 to MD_customization_for_SysML.mdzip#_18_3_903028d_1448291312269_537593_13833
                                }
                                part def 'Transmit Antenna and Equipment' {
                                    @OfficialCSRMProfile::'Architecture Structures Profile'::'Component';
                                    doc /* Source XMI: _18_4_1_3e4019a_1489768805478_770853_15774
                                    Stereotype Component
                                    UML kind: uml:Class */
                                    // UML generalization _18_4_1_3880181_1492191352173_304060_45877 to MD_customization_for_SysML.mdzip#_18_3_903028d_1448291312269_537593_13833
                                }
                            }
                            package 'L4.1.3.1_Behaviors' {
                                doc /* Source XMI: _19_0_2_3880181_1561134171274_440165_60490
                                UML kind: uml:Package */
                            }
                        }
                        package 'L4.1.4_Attitude Determination and Control Components' {
                            doc /* Source XMI: _18_4_1_3e4019a_1489768485809_35049_15742
                            Comment _19_0_2_3880181_1600961398556_278489_62820
                            Package for CubeSat Attitude Determination and Control components.  To be populated by a mission specific team.
                            UML kind: uml:Package */
                            package 'L4.1.4.2_Structures' {
                                doc /* Source XMI: _18_4_1_3e4019a_1489768485809_469224_15743
                                Comment _19_0_3_2b0010b_1619531913398_408198_13682 (HowTo)
                                Select Components Table / Select in Containment Tree to locate Components pkg in the Containment tree
                                Open the Components Table
                                Select Add New to add a new component to the containment tree and to the table
                                Open the Subsystem bdd
                                Drag the new component element from the containment tree to the Subsystems bdd – to the Components pkg – to the Structure pkg
                                Right click the Subsystem block, select the directed composition relationship, and drag to the new component element
                                Return to the Component Population pkg.
                                Open the CubeSat Subsystems Structures Table to see the components associated with the Subsystem
                                UML kind: uml:Package */
                                part def 'Software' {
                                    @OfficialCSRMProfile::'Architecture Structures Profile'::'Component';
                                    doc /* Source XMI: _18_4_1_3e4019a_1489768817190_694096_15776
                                    Stereotype Component
                                    UML kind: uml:Class */
                                    // UML generalization _18_4_1_3880181_1492191352183_810538_45894 to MD_customization_for_SysML.mdzip#_18_3_903028d_1448291312269_537593_13833
                                }
                                part def 'Actuator' {
                                    @OfficialCSRMProfile::'Architecture Structures Profile'::'Component';
                                    doc /* Source XMI: _18_4_1_3e4019a_1489768900651_242105_15780
                                    Stereotype Component
                                    UML kind: uml:Class */
                                    // UML generalization _18_4_1_3880181_1492191352185_255822_45897 to MD_customization_for_SysML.mdzip#_18_3_903028d_1448291312269_537593_13833
                                }
                                part def 'Sensor' {
                                    @OfficialCSRMProfile::'Architecture Structures Profile'::'Component';
                                    doc /* Source XMI: _18_4_1_3e4019a_1489768843413_403992_15778
                                    Stereotype Component
                                    UML kind: uml:Class */
                                    // UML generalization _18_4_1_3880181_1492191352185_871134_45896 to MD_customization_for_SysML.mdzip#_18_3_903028d_1448291312269_537593_13833
                                }
                            }
                            package 'L4.1.4.1_Behaviors' {
                                doc /* Source XMI: _19_0_2_3880181_1561134211106_946636_60491
                                UML kind: uml:Package */
                            }
                        }
                        package 'L4.1.5_Guidance Navigation and Control Components' {
                            doc /* Source XMI: _18_4_1_3e4019a_1489768486258_560840_15744
                            Comment _19_0_2_3880181_1600961460529_100978_62821
                            Package for CubeSat Guidance Navigation and Control components.  To be populated by a mission specific team.
                            UML kind: uml:Package */
                            package 'L4.1.5.2_Structures' {
                                doc /* Source XMI: _18_4_1_3e4019a_1489768486258_147064_15745
                                Comment _19_0_3_2b0010b_1619902386968_843531_3502 (HowTo)
                                Select Components Table / Select in Containment Tree to locate Components pkg in the Containment tree
                                Open the Components Table
                                Select Add New to add a new component to the containment tree and to the table
                                Open the Subsystem bdd
                                Drag the new component element from the containment tree to the Subsystems bdd – to the Components pkg – to the Structure pkg
                                Right click the Subsystem block, select the directed composition relationship, and drag to the new component element
                                Return to the Component Population pkg.
                                Open the CubeSat Subsystems Structures Table to see the components associated with the Subsystem
                                UML kind: uml:Package */
                                part def 'Software' {
                                    @OfficialCSRMProfile::'Architecture Structures Profile'::'Component';
                                    doc /* Source XMI: _18_4_1_3e4019a_1489768926748_916942_15782
                                    Stereotype Component
                                    UML kind: uml:Class */
                                    // UML generalization _18_4_1_3880181_1492191352188_192061_45900 to MD_customization_for_SysML.mdzip#_18_3_903028d_1448291312269_537593_13833
                                }
                                part def 'Accelerometer' {
                                    @OfficialCSRMProfile::'Architecture Structures Profile'::'Component';
                                    doc /* Source XMI: _18_4_1_3e4019a_1489769029630_744670_15786
                                    Stereotype Component
                                    UML kind: uml:Class */
                                    // UML generalization _18_4_1_3880181_1492191352188_6194_45901 to MD_customization_for_SysML.mdzip#_18_3_903028d_1448291312269_537593_13833
                                }
                                part def 'GNSS Receiver' {
                                    @OfficialCSRMProfile::'Architecture Structures Profile'::'Component';
                                    doc /* Source XMI: _18_4_1_3e4019a_1489769039217_2330_15788
                                    Stereotype Component
                                    UML kind: uml:Class */
                                    // UML generalization _18_4_1_3880181_1492191352186_481987_45898 to MD_customization_for_SysML.mdzip#_18_3_903028d_1448291312269_537593_13833
                                }
                            }
                            package 'L4.1.5.1_Behaviors' {
                                doc /* Source XMI: _19_0_2_3880181_1561134348311_995545_60492
                                UML kind: uml:Package */
                            }
                        }
                        package 'L4.1.6_Structures and Mechanisms Components' {
                            doc /* Source XMI: _18_4_1_3e4019a_1489768492806_924551_15746
                            Comment _19_0_2_3880181_1600961524644_440088_62822
                            Package for CubeSat Structures and Mechanisms components.  To be populated by a mission specific team.
                            UML kind: uml:Package */
                            package 'L4.1.6.1_Behaviors' {
                                doc /* Source XMI: _19_0_2_3880181_1561134396645_824648_60493
                                UML kind: uml:Package */
                            }
                            package 'L4.1.6.2_Structures' {
                                doc /* Source XMI: _18_4_1_3e4019a_1489768492806_721988_15747
                                Comment _19_0_3_2b0010b_1619902427338_888325_3658 (HowTo)
                                Select Components Table / Select in Containment Tree to locate Components pkg in the Containment tree
                                Open the Components Table
                                Select Add New to add a new component to the containment tree and to the table
                                Open the Subsystem bdd
                                Drag the new component element from the containment tree to the Subsystems bdd – to the Components pkg – to the Structure pkg
                                Right click the Subsystem block, select the directed composition relationship, and drag to the new component element
                                Return to the Component Population pkg.
                                Open the CubeSat Subsystems Structures Table to see the components associated with the Subsystem
                                UML kind: uml:Package */
                                part def 'Static Mount' {
                                    @OfficialCSRMProfile::'Architecture Structures Profile'::'Component';
                                    doc /* Source XMI: _18_4_1_3e4019a_1489769118630_914296_15790
                                    Stereotype Component
                                    UML kind: uml:Class */
                                    // UML generalization _18_4_1_3880181_1492191352170_658063_45872 to MD_customization_for_SysML.mdzip#_18_3_903028d_1448291312269_537593_13833
                                }
                                part def 'Deployable Mount' {
                                    @OfficialCSRMProfile::'Architecture Structures Profile'::'Component';
                                    doc /* Source XMI: _18_4_1_3e4019a_1489769128357_370503_15792
                                    Stereotype Component
                                    UML kind: uml:Class */
                                    // UML generalization _18_4_1_3880181_1492191352170_472729_45871 to MD_customization_for_SysML.mdzip#_18_3_903028d_1448291312269_537593_13833
                                }
                                part def 'Actuated Mount' {
                                    @OfficialCSRMProfile::'Architecture Structures Profile'::'Component';
                                    doc /* Source XMI: _18_4_1_3e4019a_1489769142115_856032_15796
                                    Stereotype Component
                                    UML kind: uml:Class */
                                    // UML generalization _18_4_1_3880181_1492191352169_612263_45870 to MD_customization_for_SysML.mdzip#_18_3_903028d_1448291312269_537593_13833
                                }
                            }
                        }
                        package 'L4.1.7_Power Components' {
                            doc /* Source XMI: _18_4_1_3e4019a_1489768493379_436995_15748
                            Comment _19_0_2_3880181_1600961628751_377249_62823
                            Package for CubeSat Power components.  To be populated by a mission specific team.
                            UML kind: uml:Package */
                            package 'L4.1.7.2_Structures' {
                                doc /* Source XMI: _18_4_1_3e4019a_1489768493379_596543_15749
                                Comment _19_0_3_2b0010b_1619902495410_957771_3742 (HowTo)
                                Select Components Table / Select in Containment Tree to locate Components pkg in the Containment tree
                                Open the Components Table
                                Select Add New to add a new component to the containment tree and to the table
                                Open the Subsystem bdd
                                Drag the new component element from the containment tree to the Subsystems bdd – to the Components pkg – to the Structure pkg
                                Right click the Subsystem block, select the directed composition relationship, and drag to the new component element
                                Return to the Component Population pkg.
                                Open the CubeSat Subsystems Structures Table to see the components associated with the Subsystem
                                UML kind: uml:Package */
                                part def 'Processor and Memory' {
                                    @OfficialCSRMProfile::'Architecture Structures Profile'::'Component';
                                    doc /* Source XMI: _18_4_1_3e4019a_1489768621567_166101_15770
                                    Stereotype Component
                                    UML kind: uml:Class */
                                    // UML generalization _18_4_1_3880181_1492191352179_62972_45888 to MD_customization_for_SysML.mdzip#_18_3_903028d_1448291312269_537593_13833
                                }
                                part def 'Software' {
                                    @OfficialCSRMProfile::'Architecture Structures Profile'::'Component';
                                    doc /* Source XMI: _18_4_1_3e4019a_1489769180766_666463_15798
                                    Stereotype Component
                                    UML kind: uml:Class */
                                    // UML generalization _18_4_1_3880181_1492191352181_323179_45891 to MD_customization_for_SysML.mdzip#_18_3_903028d_1448291312269_537593_13833
                                }
                                part def 'Solar Arrays' {
                                    @OfficialCSRMProfile::'Architecture Structures Profile'::'Component';
                                    doc /* Source XMI: _18_4_1_3e4019a_1489769190724_172852_15800
                                    Stereotype Component
                                    UML kind: uml:Class */
                                    // UML generalization _18_4_1_3880181_1492191352180_39210_45890 to MD_customization_for_SysML.mdzip#_18_3_903028d_1448291312269_537593_13833
                                }
                                part def 'Batteries' {
                                    @OfficialCSRMProfile::'Architecture Structures Profile'::'Component';
                                    doc /* Source XMI: _18_4_1_3e4019a_1489769201063_373794_15802
                                    Stereotype Component
                                    UML kind: uml:Class */
                                    // UML generalization _18_4_1_3880181_1492191352181_569190_45892 to MD_customization_for_SysML.mdzip#_18_3_903028d_1448291312269_537593_13833
                                }
                                part def 'Regulators and Converters' {
                                    @OfficialCSRMProfile::'Architecture Structures Profile'::'Component';
                                    doc /* Source XMI: _18_4_1_3e4019a_1489769207094_764375_15804
                                    Stereotype Component
                                    UML kind: uml:Class */
                                    // UML generalization _18_4_1_3880181_1492191352179_233684_45889 to MD_customization_for_SysML.mdzip#_18_3_903028d_1448291312269_537593_13833
                                }
                                part def 'Power Circuits and Switches' {
                                    @OfficialCSRMProfile::'Architecture Structures Profile'::'Component';
                                    doc /* Source XMI: _18_4_1_3e4019a_1489769219591_806033_15806
                                    Stereotype Component
                                    UML kind: uml:Class */
                                    // UML generalization _18_4_1_3880181_1492191352182_523947_45893 to MD_customization_for_SysML.mdzip#_18_3_903028d_1448291312269_537593_13833
                                }
                            }
                            package 'L4.1.7.1_Behaviors' {
                                doc /* Source XMI: _19_0_2_3880181_1561134436431_503305_60494
                                UML kind: uml:Package */
                            }
                        }
                        package 'L4.1.8_Thermal Components' {
                            doc /* Source XMI: _18_4_1_3e4019a_1489768494022_233468_15750
                            Comment _19_0_2_3880181_1600961658923_438763_62824
                            Package for CubeSat Mission Thermal components.  To be populated by a mission specific team.
                            UML kind: uml:Package */
                            package 'L4.1.8.2_Structures' {
                                doc /* Source XMI: _18_4_1_3e4019a_1489768494022_542248_15751
                                Comment _19_0_3_2b0010b_1619902548696_727334_3942 (HowTo)
                                Select Components Table / Select in Containment Tree to locate Components pkg in the Containment tree
                                Open the Components Table
                                Select Add New to add a new component to the containment tree and to the table
                                Open the Subsystem bdd
                                Drag the new component element from the containment tree to the Subsystems bdd – to the Components pkg – to the Structure pkg
                                Right click the Subsystem block, select the directed composition relationship, and drag to the new component element
                                Return to the Component Population pkg.
                                Open the CubeSat Subsystems Structures Table to see the components associated with the Subsystem
                                UML kind: uml:Package */
                                part def 'Processor and Memory' {
                                    @OfficialCSRMProfile::'Architecture Structures Profile'::'Component';
                                    doc /* Source XMI: _18_4_1_3e4019a_1489768619199_363897_15768
                                    Stereotype Component
                                    UML kind: uml:Class */
                                    // UML generalization _18_4_1_3880181_1492191352178_412083_45887 to MD_customization_for_SysML.mdzip#_18_3_903028d_1448291312269_537593_13833
                                }
                                part def 'Thermal Sensors, Sources, and Sinks' {
                                    @OfficialCSRMProfile::'Architecture Structures Profile'::'Component';
                                    doc /* Source XMI: _18_4_1_3e4019a_1489769248111_377457_15810
                                    Stereotype Component
                                    UML kind: uml:Class */
                                    // UML generalization _18_4_1_3880181_1492191352177_448446_45886 to MD_customization_for_SysML.mdzip#_18_3_903028d_1448291312269_537593_13833
                                }
                                part def 'Software' {
                                    @OfficialCSRMProfile::'Architecture Structures Profile'::'Component';
                                    doc /* Source XMI: _18_4_1_3e4019a_1489769233008_677974_15808
                                    Stereotype Component
                                    UML kind: uml:Class */
                                    // UML generalization _18_4_1_3880181_1492191352177_712625_45885 to MD_customization_for_SysML.mdzip#_18_3_903028d_1448291312269_537593_13833
                                }
                            }
                            package 'L4.1.8.1_Behaviors' {
                                doc /* Source XMI: _19_0_2_3880181_1561134480282_459644_60495
                                UML kind: uml:Package */
                            }
                        }
                        package 'L4.1.9_Propulsion Components' {
                            doc /* Source XMI: _18_4_1_3e4019a_1489768495071_339453_15752
                            Comment _19_0_2_3880181_1600961721193_238236_62825
                            Package for CubeSat Propulsion components.  To be populated by a mission specific team.
                            UML kind: uml:Package */
                            package 'L4.1.9.2_Structures' {
                                doc /* Source XMI: _18_4_1_3e4019a_1489768495071_466982_15753
                                Comment _19_0_3_2b0010b_1619902590886_921104_4174 (HowTo)
                                Select Components Table / Select in Containment Tree to locate Components pkg in the Containment tree
                                Open the Components Table
                                Select Add New to add a new component to the containment tree and to the table
                                Open the Subsystem bdd
                                Drag the new component element from the containment tree to the Subsystems bdd – to the Components pkg – to the Structure pkg
                                Right click the Subsystem block, select the directed composition relationship, and drag to the new component element
                                Return to the Component Population pkg.
                                Open the CubeSat Subsystems Structures Table to see the components associated with the Subsystem
                                UML kind: uml:Package */
                                part def 'Processor and Memory' {
                                    @OfficialCSRMProfile::'Architecture Structures Profile'::'Component';
                                    doc /* Source XMI: _18_4_1_3e4019a_1489768617823_207025_15766
                                    Stereotype Component
                                    UML kind: uml:Class */
                                    // UML generalization _18_4_1_3880181_1492191352176_412659_45883 to MD_customization_for_SysML.mdzip#_18_3_903028d_1448291312269_537593_13833
                                }
                                part def 'Software' {
                                    @OfficialCSRMProfile::'Architecture Structures Profile'::'Component';
                                    doc /* Source XMI: _18_4_1_3e4019a_1489769279513_591992_15812
                                    Stereotype Component
                                    UML kind: uml:Class */
                                    // UML generalization _18_4_1_3880181_1492191352176_900584_45884 to MD_customization_for_SysML.mdzip#_18_3_903028d_1448291312269_537593_13833
                                }
                                part def 'Propellant Storage' {
                                    @OfficialCSRMProfile::'Architecture Structures Profile'::'Component';
                                    doc /* Source XMI: _18_4_1_3e4019a_1489769284909_472559_15814
                                    Stereotype Component
                                    UML kind: uml:Class */
                                    // UML generalization _18_4_1_3880181_1492191352175_565350_45882 to MD_customization_for_SysML.mdzip#_18_3_903028d_1448291312269_537593_13833
                                }
                                part def 'Propellant Control' {
                                    @OfficialCSRMProfile::'Architecture Structures Profile'::'Component';
                                    doc /* Source XMI: _18_4_1_3e4019a_1489769298016_896824_15816
                                    Stereotype Component
                                    UML kind: uml:Class */
                                    // UML generalization _18_4_1_3880181_1492191352175_878176_45881 to MD_customization_for_SysML.mdzip#_18_3_903028d_1448291312269_537593_13833
                                }
                                part def 'Thrusters' {
                                    @OfficialCSRMProfile::'Architecture Structures Profile'::'Component';
                                    doc /* Source XMI: _18_4_1_3e4019a_1489769312673_631299_15818
                                    Stereotype Component
                                    UML kind: uml:Class */
                                    // UML generalization _18_4_1_3880181_1492191352174_962985_45880 to MD_customization_for_SysML.mdzip#_18_3_903028d_1448291312269_537593_13833
                                }
                            }
                            package 'L4.1.9.1_Behaviors' {
                                doc /* Source XMI: _19_0_2_3880181_1561134036974_299933_60488
                                UML kind: uml:Package */
                            }
                        }
                        package 'L4.1.0_Shared Components' {
                            doc /* Source XMI: _18_4_1_3880181_1494340863701_234886_51170
                            Comment _19_0_2_3880181_1600960526979_608357_62816
                            Package for CubeSat subsystem Shared components.  To be populated by a mission specific team.
                            UML kind: uml:Package */
                            package 'L4.1.0.2_Structures' {
                                doc /* Source XMI: _18_4_1_3880181_1494361487994_459370_52286
                                Comment _19_0_3_2b0010b_1619902200762_221314_2734 (HowTo)
                                Select Components Table / Select in Containment Tree to locate Components pkg in the Containment tree
                                Open the Components Table
                                Select Add New to add a new component to the containment tree and to the table
                                Open the Shared Comonents  bdd
                                Drag the new component element from the containment tree to the Structure pkg
                                UML kind: uml:Package */
                                part def 'Shared Processor and Memory' {
                                    @OfficialCSRMProfile::'Architecture Structures Profile'::'Component';
                                    doc /* Source XMI: _18_4_1_3880181_1494340978082_527489_51171
                                    Stereotype Component
                                    UML kind: uml:Class */
                                }
                            }
                            package 'L4.1.0.1_Behaviors' {
                                doc /* Source XMI: _19_0_2_3880181_1561133872101_183149_60486
                                UML kind: uml:Package */
                            }
                        }
                    }
                    package 'L4.2_Ground Subsystems Components' {
                        doc /* Source XMI: _18_4_1_3e4019a_1489768409745_534032_15739
                        Comment _19_0_2_3880181_1600962504548_499099_62866
                        The package for Ground subsystems components.  To be populated by a mission specific team.
                        Comment _19_0_2_3880181_1637335870675_894904_56348 (Explanation)
                        Ground Components - Population
                        UML kind: uml:Package */
                        package 'L4.2.1_Plan and Schedule Components' {
                            doc /* Source XMI: _18_4_1_3880181_1494256915371_691905_52026
                            Comment _19_0_2_3880181_1600962765338_267215_62868
                            Package for Ground Plan and Schedule subsystem components.  To be populated by a mission specific team.
                            UML kind: uml:Package */
                            package 'L4.2.1.2_Structures' {
                                doc /* Source XMI: _19_0_2_3880181_1561132709477_981085_60330
                                Comment _19_0_3_2b0010b_1619547827014_120085_33580 (HowTo)
                                Select Components Table / Select in Containment Tree to locate Components pkg in the Containment tree
                                Open the Components Table
                                Select Add New to add a new component to the containment tree and to the table
                                Open the Subsystem bdd
                                Drag the new component element from the containment tree to the Subsystems bdd – to the Components pkg – to the Structure pkg
                                Right click the Subsystem block, select the directed composition relationship, and drag to the new component element
                                Return to the Component Population pkg.
                                Open the Ground Subsystems Structures Table to see the components associated with the Subsystem
                                UML kind: uml:Package */
                                part def 'Software' {
                                    @OfficialCSRMProfile::'Architecture Structures Profile'::'Component';
                                    doc /* Source XMI: _19_0_2_3880181_1561140070160_102171_60362
                                    Stereotype Component
                                    UML kind: uml:Class */
                                }
                                part def 'Hardware' {
                                    @OfficialCSRMProfile::'Architecture Structures Profile'::'Component';
                                    doc /* Source XMI: _19_0_2_3880181_1561140096721_590968_60364
                                    Stereotype Component
                                    UML kind: uml:Class */
                                }
                                part def 'Procedures' {
                                    @OfficialCSRMProfile::'Architecture Structures Profile'::'Component';
                                    doc /* Source XMI: _19_0_2_3880181_1561140112822_418165_60366
                                    Stereotype Component
                                    UML kind: uml:Class */
                                }
                            }
                            package 'L4.2.1.1_Behaviors' {
                                doc /* Source XMI: _19_0_2_3880181_1561133031535_612490_60332
                                UML kind: uml:Package */
                            }
                        }
                        package 'L4.2.3_Ground Equipment Control Components' {
                            doc /* Source XMI: _18_4_1_3880181_1494257025685_326544_52027
                            Comment _19_0_2_3880181_1600963123184_71306_62910
                            Package for Ground Equipment Control subsystem components.  To be populated by a mission specific team.
                            UML kind: uml:Package */
                            package 'L4.2.3.1_Behaviors' {
                                doc /* Source XMI: _19_0_2_3880181_1561133149190_713311_60334
                                UML kind: uml:Package */
                            }
                            package 'L4.2.3.2_Structures' {
                                doc /* Source XMI: _19_0_2_3880181_1561133205520_24912_60335
                                Comment _19_0_3_2b0010b_1619535036177_303181_15321 (HowTo)
                                Select Components Table / Select in Containment Tree to locate Components pkg in the Containment tree
                                Open the Components Table
                                Select Add New to add a new component to the containment tree and to the table
                                Open the Subsystem bdd
                                Drag the new component element from the containment tree to the Subsystems bdd – to the Components pkg – to the Structure pkg
                                Right click the Subsystem block, select the directed composition relationship, and drag to the new component element
                                Return to the Component Population pkg.
                                Open the Ground Subsystems Structures Table to see the components associated with the Subsystem
                                UML kind: uml:Package */
                                part def 'Software' {
                                    @OfficialCSRMProfile::'Architecture Structures Profile'::'Component';
                                    doc /* Source XMI: _19_0_2_3880181_1561244785934_257889_60907
                                    Stereotype Component
                                    UML kind: uml:Class */
                                }
                                part def 'Hardware' {
                                    @OfficialCSRMProfile::'Architecture Structures Profile'::'Component';
                                    doc /* Source XMI: _19_0_2_3880181_1561244849588_217848_60934
                                    Stereotype Component
                                    UML kind: uml:Class */
                                }
                                part def 'Procedures' {
                                    @OfficialCSRMProfile::'Architecture Structures Profile'::'Component';
                                    doc /* Source XMI: _19_0_2_3880181_1561244880914_430932_60938
                                    Stereotype Component
                                    UML kind: uml:Class */
                                }
                            }
                        }
                        package 'L4.2.4_Space-Ground Communication Components' {
                            doc /* Source XMI: _18_4_1_3880181_1494257069111_977393_52028
                            Comment _19_0_2_3880181_1600963183749_485793_62911
                            Package for Ground Space-Ground Communication subsystem components.  To be populated by a mission specific team.
                            UML kind: uml:Package */
                            package 'L4.2.4.1_Behaviors' {
                                doc /* Source XMI: _19_0_2_3880181_1561133239898_445616_60336
                                UML kind: uml:Package */
                            }
                            package 'L4.2.4.2_Structures' {
                                doc /* Source XMI: _19_0_2_3880181_1561133307757_308563_60477
                                Comment _19_0_3_2b0010b_1619547927423_821169_33743 (HowTo)
                                Select Components Table / Select in Containment Tree to locate Components pkg in the Containment tree
                                Open the Components Table
                                Select Add New to add a new component to the containment tree and to the table
                                Open the Subsystem bdd
                                Drag the new component element from the containment tree to the Subsystems bdd – to the Components pkg – to the Structure pkg
                                Right click the Subsystem block, select the directed composition relationship, and drag to the new component element
                                Return to the Component Population pkg.
                                Open the Ground Subsystems Structures Table to see the components associated with the Subsystem
                                UML kind: uml:Package */
                                part def 'Software' {
                                    @OfficialCSRMProfile::'Architecture Structures Profile'::'Component';
                                    doc /* Source XMI: _19_0_2_3880181_1561245140395_246710_60952
                                    Stereotype Component
                                    UML kind: uml:Class */
                                }
                                part def 'Hardware' {
                                    @OfficialCSRMProfile::'Architecture Structures Profile'::'Component';
                                    doc /* Source XMI: _19_0_2_3880181_1561245192010_65619_60979
                                    Stereotype Component
                                    UML kind: uml:Class */
                                }
                                part def 'Procedures' {
                                    @OfficialCSRMProfile::'Architecture Structures Profile'::'Component';
                                    doc /* Source XMI: _19_0_2_3880181_1561245203929_935228_60983
                                    Stereotype Component
                                    UML kind: uml:Class */
                                }
                            }
                        }
                        package 'L4.2.2_Spacecraft Command Components' {
                            doc /* Source XMI: _18_4_1_3880181_1494257117093_522446_52029
                            Comment _19_0_2_3880181_1600962993922_847980_62869
                            Package for Ground Spacecraft Command subsystem components.  To be populated by a mission specific team.
                            UML kind: uml:Package */
                            package 'L4.2.2.2_Structures' {
                                doc /* Source XMI: _19_0_2_3880181_1561132927545_296089_60331
                                Comment _19_0_3_2b0010b_1619547844627_531601_33642 (HowTo)
                                Select Components Table / Select in Containment Tree to locate Components pkg in the Containment tree
                                Open the Components Table
                                Select Add New to add a new component to the containment tree and to the table
                                Open the Subsystem bdd
                                Drag the new component element from the containment tree to the Subsystems bdd – to the Components pkg – to the Structure pkg
                                Right click the Subsystem block, select the directed composition relationship, and drag to the new component element
                                Return to the Component Population pkg.
                                Open the Ground Subsystems Structures Table to see the components associated with the Subsystem
                                UML kind: uml:Package */
                                part def 'Software' {
                                    @OfficialCSRMProfile::'Architecture Structures Profile'::'Component';
                                    doc /* Source XMI: _19_0_2_3880181_1561244679043_729355_60870
                                    Stereotype Component
                                    UML kind: uml:Class */
                                }
                                part def 'Hardware' {
                                    @OfficialCSRMProfile::'Architecture Structures Profile'::'Component';
                                    doc /* Source XMI: _19_0_2_3880181_1561244924860_272284_60944
                                    Stereotype Component
                                    UML kind: uml:Class */
                                }
                                part def 'Procedures' {
                                    @OfficialCSRMProfile::'Architecture Structures Profile'::'Component';
                                    doc /* Source XMI: _19_0_2_3880181_1561244973154_477653_60948
                                    Stereotype Component
                                    UML kind: uml:Class */
                                }
                            }
                            package 'L4.2.2.1_Behaviors' {
                                doc /* Source XMI: _19_0_2_3880181_1561133075413_386376_60333
                                UML kind: uml:Package */
                            }
                        }
                        package 'L4.2.5_Mission Data Processing Components' {
                            doc /* Source XMI: _18_4_1_3880181_1494257189578_449302_52030
                            Comment _19_0_2_3880181_1600963254946_703281_62912
                            Package for Ground Mission Data Processing subsystem components.  To be populated by a mission specific team.
                            UML kind: uml:Package */
                            package 'L4.2.5.1_Behaviors' {
                                doc /* Source XMI: _19_0_2_3880181_1561133351412_502079_60478
                                UML kind: uml:Package */
                            }
                            package 'L4.2.5.2_Structures' {
                                doc /* Source XMI: _19_0_2_3880181_1561133386583_913507_60479
                                Comment _19_0_3_2b0010b_1619547449386_238022_33005 (HowTo)
                                Select Components Table / Select in Containment Tree to locate Components pkg in the Containment tree
                                Open the Components Table
                                Select Add New to add a new component to the containment tree and to the table
                                Open the Subsystem bdd
                                Drag the new component element from the containment tree to the Subsystems bdd – to the Components pkg – to the Structure pkg
                                Right click the Subsystem block, select the directed composition relationship, and drag to the new component element
                                Return to the Component Population pkg.
                                Open the Ground Subsystems Structures to see the components associated with the Subsystem
                                UML kind: uml:Package */
                                part def 'Software' {
                                    @OfficialCSRMProfile::'Architecture Structures Profile'::'Component';
                                    doc /* Source XMI: _19_0_2_3880181_1561245259757_759124_61027
                                    Stereotype Component
                                    UML kind: uml:Class */
                                }
                                part def 'Hardware' {
                                    @OfficialCSRMProfile::'Architecture Structures Profile'::'Component';
                                    doc /* Source XMI: _19_0_2_3880181_1561245353070_159433_61056
                                    Stereotype Component
                                    UML kind: uml:Class */
                                }
                                part def 'Procedures' {
                                    @OfficialCSRMProfile::'Architecture Structures Profile'::'Component';
                                    doc /* Source XMI: _19_0_2_3880181_1561245412683_544678_61060
                                    Stereotype Component
                                    UML kind: uml:Class */
                                }
                            }
                        }
                        package 'L4.2.6_Mission Data Dissemination Components' {
                            doc /* Source XMI: _18_4_1_3880181_1494257309757_236377_52031
                            Comment _19_0_2_3880181_1600963320796_439814_62913
                            Package for Ground Mission Data Dissemination subsystem components.  To be populated by a mission specific team.
                            UML kind: uml:Package */
                            package 'L4.2.6.1_Behaviors' {
                                doc /* Source XMI: _19_0_2_3880181_1561133441219_999778_60480
                                UML kind: uml:Package */
                            }
                            package 'L4.2.6.2_Structures' {
                                doc /* Source XMI: _19_0_2_3880181_1561133491087_548627_60481
                                Comment _19_0_3_2b0010b_1619547474934_947522_33067 (HowTo)
                                Select Components Table / Select in Containment Tree to locate Components pkg in the Containment tree
                                Open the Components Table
                                Select Add New to add a new component to the containment tree and to the table
                                Open the Subsystem bdd
                                Drag the new component element from the containment tree to the Subsystems bdd – to the Components pkg – to the Structure pkg
                                Right click the Subsystem block, select the directed composition relationship, and drag to the new component element
                                Return to the Component Population pkg.
                                Open the Ground Subsystems Structures Table to see the components associated with the Subsystem
                                UML kind: uml:Package */
                                part def 'Software' {
                                    @OfficialCSRMProfile::'Architecture Structures Profile'::'Component';
                                    doc /* Source XMI: _19_0_2_3880181_1561245478179_326375_61064
                                    Stereotype Component
                                    UML kind: uml:Class */
                                }
                                part def 'Hardware' {
                                    @OfficialCSRMProfile::'Architecture Structures Profile'::'Component';
                                    doc /* Source XMI: _19_0_2_3880181_1561245523058_466717_61091
                                    Stereotype Component
                                    UML kind: uml:Class */
                                }
                                part def 'Procedures' {
                                    @OfficialCSRMProfile::'Architecture Structures Profile'::'Component';
                                    doc /* Source XMI: _19_0_2_3880181_1561245538412_270076_61095
                                    Stereotype Component
                                    UML kind: uml:Class */
                                }
                            }
                        }
                        package 'L4.2.7_Network Components' {
                            doc /* Source XMI: _18_4_1_3880181_1494257353515_391633_52032
                            Comment _19_0_2_3880181_1600963409879_194933_62914
                            Package for Ground Network subsystem components.  To be populated by a mission specific team.
                            UML kind: uml:Package */
                            package 'L4.2.7.1_Behaviors' {
                                doc /* Source XMI: _19_0_2_3880181_1561133540757_627645_60482
                                UML kind: uml:Package */
                            }
                            package 'L4.2.7.2_Structures' {
                                doc /* Source XMI: _19_0_2_3880181_1561133579420_27542_60483
                                Comment _19_0_3_2b0010b_1619547507526_953655_33129 (HowTo)
                                Select Components Table / Select in Containment Tree to locate Components pkg in the Containment tree
                                Open the Components Table
                                Select Add New to add a new component to the containment tree and to the table
                                Open the Subsystem bdd
                                Drag the new component element from the containment tree to the Subsystems bdd – to the Components pkg – to the Structure pkg
                                Right click the Subsystem block, select the directed composition relationship, and drag to the new component element
                                Return to the Component Population pkg.
                                Open the Ground Subsystems Structures Table to see the components associated with the Subsystem
                                UML kind: uml:Package */
                                part def 'Hardware' {
                                    @OfficialCSRMProfile::'Architecture Structures Profile'::'Component';
                                    doc /* Source XMI: _19_0_2_3880181_1561296853724_451978_62430
                                    Stereotype Component
                                    UML kind: uml:Class */
                                }
                                part def 'Procedures' {
                                    @OfficialCSRMProfile::'Architecture Structures Profile'::'Component';
                                    doc /* Source XMI: _19_0_2_3880181_1561296916180_628507_62434
                                    Stereotype Component
                                    UML kind: uml:Class */
                                }
                                part def 'Software' {
                                    @OfficialCSRMProfile::'Architecture Structures Profile'::'Component';
                                    doc /* Source XMI: _19_0_2_3880181_1561296894472_40705_62432
                                    Stereotype Component
                                    UML kind: uml:Class */
                                }
                            }
                        }
                        package 'L4.2.8_Facility Components' {
                            doc /* Source XMI: _19_0_2_3880181_1652707326265_865117_58584
                            UML kind: uml:Package */
                            package 'L4.2.8.1_Behaviors' {
                                doc /* Source XMI: _19_0_2_3880181_1652707554366_490356_58585
                                UML kind: uml:Package */
                            }
                            package 'L4.2.8.2_Structures' {
                                doc /* Source XMI: _19_0_2_3880181_1652707623734_850342_58586
                                Comment _19_0_2_3880181_1652713997645_431059_58932 (HowTo)
                                Select Components Table / Select in Containment Tree to locate Components pkg in the Containment tree
                                Open the Components Table
                                Select Add New to add a new component to the containment tree and to the table
                                Open the Subsystem bdd
                                Drag the new component element from the containment tree to the Subsystems bdd – to the Components pkg – to the Structure pkg
                                Right click the Subsystem block, select the directed composition relationship, and drag to the new component element
                                Return to the Component Population pkg.
                                Open the Ground Subsystems Structures Table to see the components associated with the Subsystem
                                UML kind: uml:Package */
                                part def 'Room' {
                                    @OfficialCSRMProfile::'Architecture Structures Profile'::'Component';
                                    doc /* Source XMI: _19_0_2_3880181_1652708601584_552665_58684
                                    Stereotype Component
                                    UML kind: uml:Class */
                                }
                                part def 'Room 2' {
                                    @OfficialCSRMProfile::'Architecture Structures Profile'::'Component';
                                    doc /* Source XMI: _19_0_2_3880181_1652714230754_79149_58946
                                    Stereotype Component
                                    UML kind: uml:Class */
                                }
                            }
                        }
                    }
                }
                package 'L3_Subsystems' {
                    doc /* Source XMI: _18_0_6_3e4019a_1472151507117_529585_12343
                    Comment _19_0_2_3880181_1600787384620_440936_62951
                    The package for CubeSat subsystems and Ground subsystems.
                    The CubeSat and Ground subsystems are generically and loosely defined as a starting point for the mission specific CubeSat team.
                    The CubeSat team determines what subsystem capabilities are needed and whether they are provided by software, hardware, persistent data, or operator procedures.
                    UML kind: uml:Package */
                    package 'L3.1_CubeSat Subsystems' {
                        doc /* Source XMI: _18_0_6_3e4019a_1472151552169_401641_13486
                        Comment _19_0_2_3880181_1600957719623_426706_62600
                        The package of CubeSat subsystems behaviors and structures.
                        UML kind: uml:Package */
                        package 'L3.1.2_Structures' {
                            doc /* Source XMI: _18_0_6_3e4019a_1472151563832_967896_14086
                            Comment _19_0_2_3880181_1600957964529_603967_62602
                            The package of CubeSat subsystems structures:
                            Mission Payload
                            Command and Data Handling
                            Communication
                            Attitude Determination and Control
                            Guidance Navigation and Control
                            Structures and Mechanisms
                            Power
                            Thermal
                            Propulsion
                            Comment _19_0_3_2b0010b_1619533481548_623077_14698 (HowTo)
                            Select CubeSat Subsystems Structures Table / Select in Containment Tree to locate Subsystems pkg in the Containment tree
                            Open the CubeSat Subsystems Structures table and select Add New to add a new subsystem the containment tree and to the table.
                            Drag the new subsystem element from the containment tree to the CubeSat Subsystems bdd
                            Drag the new subsystem element from the containment tree to the Space Segment bdd.
                            Right click the Cubesat block and select directed composition and drag to the new subsystem element.
                            Open the CubeSat Structures Table and right click on Refresh to make the new subsystem a CubeSat part.
                            Comment _19_0_2_3880181_1637333440978_181346_55897 (Explanation)
                            CubeSat Subsystems - Population
                            UML kind: uml:Package */
                            part def 'Thermal Subsystem' {
                                doc /* Source XMI: _18_0_6_3e4019a_1472151609450_855672_15831
                                Stereotype Subsystem
                                UML kind: uml:Class */
                                // UML generalization _18_4_1_3880181_1492191352166_832697_45866 to MD_customization_for_SysML.mdzip#_18_3_903028d_1448291312269_537593_13833
                                part 'property_1' : OfficialCSRM::'Data'::'01 - CubeSat System Reference Model'::'5 - Architecture'::'L4_Components'::'L4.1_CubeSat Subsystems Components'::'L4.1.8_Thermal Components'::'L4.1.8.2_Structures'::'Thermal Sensors, Sources, and Sinks' {
                                    doc /* Source XMI: _18_5_1_3880181_1505057858385_254941_62958
                                    Stereotype PartProperty
                                    UML aggregation: composite
                                    UML association: _18_5_1_3880181_1505057858385_74662_62957 */
                                }
                                part 'processor and Memory' : OfficialCSRM::'Data'::'01 - CubeSat System Reference Model'::'5 - Architecture'::'L4_Components'::'L4.1_CubeSat Subsystems Components'::'L4.1.8_Thermal Components'::'L4.1.8.2_Structures'::'Processor and Memory' {
                                    doc /* Source XMI: _18_5_1_3880181_1505057879514_227931_62986
                                    Stereotype PartProperty
                                    UML aggregation: composite
                                    UML association: _18_5_1_3880181_1505057879514_545440_62985 */
                                }
                                part 'software' : OfficialCSRM::'Data'::'01 - CubeSat System Reference Model'::'5 - Architecture'::'L4_Components'::'L4.1_CubeSat Subsystems Components'::'L4.1.8_Thermal Components'::'L4.1.8.2_Structures'::'Software' {
                                    doc /* Source XMI: _18_5_1_3880181_1505057887250_36678_63016
                                    Stereotype PartProperty
                                    UML aggregation: composite
                                    UML association: _18_5_1_3880181_1505057887250_935444_63015 */
                                }
                            }
                            part def 'Propulsion Subsystem' {
                                doc /* Source XMI: _18_0_6_3e4019a_1472151609451_731321_15833
                                Stereotype Subsystem
                                UML kind: uml:Class */
                                // UML generalization _18_4_1_3880181_1492191352165_392776_45865 to MD_customization_for_SysML.mdzip#_18_3_903028d_1448291312269_537593_13833
                                part 'propellant Storage' : OfficialCSRM::'Data'::'01 - CubeSat System Reference Model'::'5 - Architecture'::'L4_Components'::'L4.1_CubeSat Subsystems Components'::'L4.1.9_Propulsion Components'::'L4.1.9.2_Structures'::'Propellant Storage' {
                                    doc /* Source XMI: _18_5_1_3880181_1505056214765_70129_62115
                                    Stereotype PartProperty
                                    UML aggregation: composite
                                    UML association: _18_5_1_3880181_1505056214765_993952_62114 */
                                }
                                part 'propellant Control' : OfficialCSRM::'Data'::'01 - CubeSat System Reference Model'::'5 - Architecture'::'L4_Components'::'L4.1_CubeSat Subsystems Components'::'L4.1.9_Propulsion Components'::'L4.1.9.2_Structures'::'Propellant Control' {
                                    doc /* Source XMI: _18_5_1_3880181_1505056226158_314629_62145
                                    Stereotype PartProperty
                                    UML aggregation: composite
                                    UML association: _18_5_1_3880181_1505056226158_342495_62144 */
                                }
                                part 'thrusters' : OfficialCSRM::'Data'::'01 - CubeSat System Reference Model'::'5 - Architecture'::'L4_Components'::'L4.1_CubeSat Subsystems Components'::'L4.1.9_Propulsion Components'::'L4.1.9.2_Structures'::'Thrusters' {
                                    doc /* Source XMI: _18_5_1_3880181_1505056233128_193505_62175
                                    Stereotype PartProperty
                                    UML aggregation: composite
                                    UML association: _18_5_1_3880181_1505056233128_424942_62174 */
                                }
                                part 'processor and Memory' : OfficialCSRM::'Data'::'01 - CubeSat System Reference Model'::'5 - Architecture'::'L4_Components'::'L4.1_CubeSat Subsystems Components'::'L4.1.9_Propulsion Components'::'L4.1.9.2_Structures'::'Processor and Memory' {
                                    doc /* Source XMI: _18_5_1_3880181_1505056241864_709528_62205
                                    Stereotype PartProperty
                                    UML aggregation: composite
                                    UML association: _18_5_1_3880181_1505056241864_595199_62204 */
                                }
                                part 'software' : OfficialCSRM::'Data'::'01 - CubeSat System Reference Model'::'5 - Architecture'::'L4_Components'::'L4.1_CubeSat Subsystems Components'::'L4.1.9_Propulsion Components'::'L4.1.9.2_Structures'::'Software' {
                                    doc /* Source XMI: _18_5_1_3880181_1505056252600_224208_62235
                                    Stereotype PartProperty
                                    UML aggregation: composite
                                    UML association: _18_5_1_3880181_1505056252584_577106_62234 */
                                }
                            }
                            part def 'Structures and Mechanisms Subsystem' {
                                doc /* Source XMI: _18_0_6_3e4019a_1472151609454_535648_15837
                                Stereotype Subsystem
                                UML kind: uml:Class */
                                // UML generalization _18_4_1_3880181_1492191352163_292935_45861 to MD_customization_for_SysML.mdzip#_18_3_903028d_1448291312269_537593_13833
                                part 'deployable Mount' : OfficialCSRM::'Data'::'01 - CubeSat System Reference Model'::'5 - Architecture'::'L4_Components'::'L4.1_CubeSat Subsystems Components'::'L4.1.6_Structures and Mechanisms Components'::'L4.1.6.2_Structures'::'Deployable Mount' {
                                    doc /* Source XMI: _18_5_1_3880181_1505056669175_349972_62583
                                    Stereotype PartProperty
                                    UML aggregation: composite
                                    UML association: _18_5_1_3880181_1505056669175_130656_62582 */
                                }
                                part 'static Mount' : OfficialCSRM::'Data'::'01 - CubeSat System Reference Model'::'5 - Architecture'::'L4_Components'::'L4.1_CubeSat Subsystems Components'::'L4.1.6_Structures and Mechanisms Components'::'L4.1.6.2_Structures'::'Static Mount' {
                                    doc /* Source XMI: _18_5_1_3880181_1505056677364_646061_62613
                                    Stereotype PartProperty
                                    UML aggregation: composite
                                    UML association: _18_5_1_3880181_1505056677364_572191_62612 */
                                }
                                part 'actuated Mount' : OfficialCSRM::'Data'::'01 - CubeSat System Reference Model'::'5 - Architecture'::'L4_Components'::'L4.1_CubeSat Subsystems Components'::'L4.1.6_Structures and Mechanisms Components'::'L4.1.6.2_Structures'::'Actuated Mount' {
                                    doc /* Source XMI: _18_5_1_3880181_1505056658220_33051_62553
                                    Stereotype PartProperty
                                    UML aggregation: composite
                                    UML association: _18_5_1_3880181_1505056658220_929903_62552 */
                                }
                            }
                            part def 'Power Subsystem' {
                                doc /* Source XMI: _18_0_6_3e4019a_1472151609455_663772_15839
                                Stereotype Subsystem
                                UML kind: uml:Class */
                                // UML generalization _18_4_1_3880181_1492191352167_651606_45867 to MD_customization_for_SysML.mdzip#_18_3_903028d_1448291312269_537593_13833
                                part 'batteries' : OfficialCSRM::'Data'::'01 - CubeSat System Reference Model'::'5 - Architecture'::'L4_Components'::'L4.1_CubeSat Subsystems Components'::'L4.1.7_Power Components'::'L4.1.7.2_Structures'::'Batteries' {
                                    doc /* Source XMI: _18_5_1_3880181_1505055429243_836355_61106
                                    Stereotype PartProperty
                                    UML aggregation: composite
                                    UML association: _18_5_1_3880181_1505055429243_905410_61105 */
                                }
                                part 'regulators and Converters' : OfficialCSRM::'Data'::'01 - CubeSat System Reference Model'::'5 - Architecture'::'L4_Components'::'L4.1_CubeSat Subsystems Components'::'L4.1.7_Power Components'::'L4.1.7.2_Structures'::'Regulators and Converters' {
                                    doc /* Source XMI: _18_5_1_3880181_1505055437901_455231_61136
                                    Stereotype PartProperty
                                    UML aggregation: composite
                                    UML association: _18_5_1_3880181_1505055437901_681839_61135 */
                                }
                                part 'solar Arrays' : OfficialCSRM::'Data'::'01 - CubeSat System Reference Model'::'5 - Architecture'::'L4_Components'::'L4.1_CubeSat Subsystems Components'::'L4.1.7_Power Components'::'L4.1.7.2_Structures'::'Solar Arrays' {
                                    doc /* Source XMI: _18_5_1_3880181_1505055446934_155733_61166
                                    Stereotype PartProperty
                                    UML aggregation: composite
                                    UML association: _18_5_1_3880181_1505055446934_975434_61165 */
                                }
                                part 'power Circuits and Switches' : OfficialCSRM::'Data'::'01 - CubeSat System Reference Model'::'5 - Architecture'::'L4_Components'::'L4.1_CubeSat Subsystems Components'::'L4.1.7_Power Components'::'L4.1.7.2_Structures'::'Power Circuits and Switches' {
                                    doc /* Source XMI: _18_5_1_3880181_1505055483722_439147_61248
                                    Stereotype PartProperty
                                    UML aggregation: composite
                                    UML association: _18_5_1_3880181_1505055483722_375264_61247 */
                                }
                                part 'processor and Memory' : OfficialCSRM::'Data'::'01 - CubeSat System Reference Model'::'5 - Architecture'::'L4_Components'::'L4.1_CubeSat Subsystems Components'::'L4.1.7_Power Components'::'L4.1.7.2_Structures'::'Processor and Memory' {
                                    doc /* Source XMI: _18_5_1_3880181_1505055492849_150646_61278
                                    Stereotype PartProperty
                                    UML aggregation: composite
                                    UML association: _18_5_1_3880181_1505055492849_804272_61277 */
                                }
                                part 'software' : OfficialCSRM::'Data'::'01 - CubeSat System Reference Model'::'5 - Architecture'::'L4_Components'::'L4.1_CubeSat Subsystems Components'::'L4.1.7_Power Components'::'L4.1.7.2_Structures'::'Software' {
                                    doc /* Source XMI: _18_5_1_3880181_1505055502585_243540_61308
                                    Stereotype PartProperty
                                    UML aggregation: composite
                                    UML association: _18_5_1_3880181_1505055502585_848240_61307 */
                                }
                            }
                            part def 'Attitude Determination and Control Subsystem' {
                                doc /* Source XMI: _18_0_6_3e4019a_1472151609452_913076_15834
                                Stereotype Subsystem
                                UML kind: uml:Class */
                                // UML generalization _18_4_1_3880181_1492191352168_535853_45868 to MD_customization_for_SysML.mdzip#_18_3_903028d_1448291312269_537593_13833
                                part 'software' : OfficialCSRM::'Data'::'01 - CubeSat System Reference Model'::'5 - Architecture'::'L4_Components'::'L4.1_CubeSat Subsystems Components'::'L4.1.4_Attitude Determination and Control Components'::'L4.1.4.2_Structures'::'Software' {
                                    doc /* Source XMI: _18_5_1_3880181_1505051904776_715917_59468
                                    Stereotype PartProperty
                                    UML aggregation: composite
                                    UML association: _18_5_1_3880181_1505051904776_311150_59467 */
                                }
                                part 'actuator' : OfficialCSRM::'Data'::'01 - CubeSat System Reference Model'::'5 - Architecture'::'L4_Components'::'L4.1_CubeSat Subsystems Components'::'L4.1.4_Attitude Determination and Control Components'::'L4.1.4.2_Structures'::'Actuator' {
                                    doc /* Source XMI: _18_5_1_3880181_1505051910340_912233_59498
                                    Stereotype PartProperty
                                    UML aggregation: composite
                                    UML association: _18_5_1_3880181_1505051910340_225127_59497 */
                                }
                                part 'sensor' : OfficialCSRM::'Data'::'01 - CubeSat System Reference Model'::'5 - Architecture'::'L4_Components'::'L4.1_CubeSat Subsystems Components'::'L4.1.4_Attitude Determination and Control Components'::'L4.1.4.2_Structures'::'Sensor' {
                                    doc /* Source XMI: _18_5_1_3880181_1505051918826_844900_59528
                                    Stereotype PartProperty
                                    UML aggregation: composite
                                    UML association: _18_5_1_3880181_1505051918826_920978_59527 */
                                }
                                part 'shared Processor and Memory' : OfficialCSRM::'Data'::'01 - CubeSat System Reference Model'::'5 - Architecture'::'L4_Components'::'L4.1_CubeSat Subsystems Components'::'L4.1.0_Shared Components'::'L4.1.0.2_Structures'::'Shared Processor and Memory' {
                                    doc /* Source XMI: _18_5_1_3880181_1505051926390_570536_59558
                                    Stereotype PartProperty
                                    UML aggregation: composite
                                    UML association: _18_5_1_3880181_1505051926390_546978_59557 */
                                }
                            }
                            part def 'Command and Data Handling Subsystem' {
                                doc /* Source XMI: _18_0_6_3e4019a_1472151609454_765346_15838
                                Stereotype Subsystem
                                UML kind: uml:Class */
                                // UML generalization _18_4_1_3880181_1492191352163_535313_45862 to MD_customization_for_SysML.mdzip#_18_3_903028d_1448291312269_537593_13833
                                part 'property_1' : OfficialCSRM::'Data'::'01 - CubeSat System Reference Model'::'5 - Architecture'::'L4_Components'::'L4.1_CubeSat Subsystems Components'::'L4.1.2_Command and Data Handling Components'::'L4.1.2.2_Structures'::'Command, Telemetry, and Data Bus' {
                                    doc /* Source XMI: _18_5_1_3880181_1505052868446_280959_59876
                                    Stereotype PartProperty
                                    UML aggregation: composite
                                    UML association: _18_5_1_3880181_1505052868446_387484_59875 */
                                }
                                part 'processor and Memory' : OfficialCSRM::'Data'::'01 - CubeSat System Reference Model'::'5 - Architecture'::'L4_Components'::'L4.1_CubeSat Subsystems Components'::'L4.1.2_Command and Data Handling Components'::'L4.1.2.2_Structures'::'Processor and Memory' {
                                    doc /* Source XMI: _18_5_1_3880181_1505052908719_471437_59956
                                    Stereotype PartProperty
                                    UML aggregation: composite
                                    UML association: _18_5_1_3880181_1505052908719_121393_59955 */
                                }
                            }
                            part def 'Communication Subsystem' {
                                doc /* Source XMI: _18_0_6_3e4019a_1472151609451_873397_15832
                                Stereotype Subsystem
                                Comment _18_0_6_3e4019a_1472151614907_861895_17611
                                UML kind: uml:Class */
                                // UML generalization _18_4_1_3880181_1492191352164_130227_45863 to MD_customization_for_SysML.mdzip#_18_3_903028d_1448291312269_537593_13833
                                part 'processor and Memory' : OfficialCSRM::'Data'::'01 - CubeSat System Reference Model'::'5 - Architecture'::'L4_Components'::'L4.1_CubeSat Subsystems Components'::'L4.1.3_Communication Components'::'L4.1.3.2_Structures'::'Processor and Memory' {
                                    doc /* Source XMI: _18_5_1_3880181_1505054228737_235187_60391
                                    Stereotype PartProperty
                                    UML aggregation: composite
                                    UML association: _18_5_1_3880181_1505054228737_659474_60390 */
                                }
                                part 'receive Antenna and Equipment' : OfficialCSRM::'Data'::'01 - CubeSat System Reference Model'::'5 - Architecture'::'L4_Components'::'L4.1_CubeSat Subsystems Components'::'L4.1.3_Communication Components'::'L4.1.3.2_Structures'::'Receive Antenna and Equipment' {
                                    doc /* Source XMI: _18_5_1_3880181_1505054238693_563290_60421
                                    Stereotype PartProperty
                                    UML aggregation: composite
                                    UML association: _18_5_1_3880181_1505054238693_239871_60420 */
                                }
                                part 'transmit Antenna and Equipment' : OfficialCSRM::'Data'::'01 - CubeSat System Reference Model'::'5 - Architecture'::'L4_Components'::'L4.1_CubeSat Subsystems Components'::'L4.1.3_Communication Components'::'L4.1.3.2_Structures'::'Transmit Antenna and Equipment' {
                                    doc /* Source XMI: _18_5_1_3880181_1505054264245_356300_60503
                                    Stereotype PartProperty
                                    UML aggregation: composite
                                    UML association: _18_5_1_3880181_1505054264245_975433_60502 */
                                }
                            }
                            part def 'Guidance Navigation and Control Subsystem' {
                                doc /* Source XMI: _18_0_6_3e4019a_1472151609456_401153_15840
                                Stereotype Subsystem
                                UML kind: uml:Class */
                                // UML generalization _18_4_1_3880181_1492191352168_206310_45869 to MD_customization_for_SysML.mdzip#_18_3_903028d_1448291312269_537593_13833
                                part 'accelerometer' : OfficialCSRM::'Data'::'01 - CubeSat System Reference Model'::'5 - Architecture'::'L4_Components'::'L4.1_CubeSat Subsystems Components'::'L4.1.5_Guidance Navigation and Control Components'::'L4.1.5.2_Structures'::'Accelerometer' {
                                    doc /* Source XMI: _18_5_1_3880181_1505050866981_110069_59248
                                    Stereotype PartProperty
                                    UML aggregation: composite
                                    UML association: _18_5_1_3880181_1505050866981_414434_59247 */
                                }
                                part 'gNSS Receiver' : OfficialCSRM::'Data'::'01 - CubeSat System Reference Model'::'5 - Architecture'::'L4_Components'::'L4.1_CubeSat Subsystems Components'::'L4.1.5_Guidance Navigation and Control Components'::'L4.1.5.2_Structures'::'GNSS Receiver' {
                                    doc /* Source XMI: _18_5_1_3880181_1505050875592_443207_59278
                                    Stereotype PartProperty
                                    UML aggregation: composite
                                    UML association: _18_5_1_3880181_1505050875592_54683_59277 */
                                }
                                part 'software' : OfficialCSRM::'Data'::'01 - CubeSat System Reference Model'::'5 - Architecture'::'L4_Components'::'L4.1_CubeSat Subsystems Components'::'L4.1.5_Guidance Navigation and Control Components'::'L4.1.5.2_Structures'::'Software' {
                                    doc /* Source XMI: _18_5_1_3880181_1505050917522_656849_59360
                                    Stereotype PartProperty
                                    UML aggregation: composite
                                    UML association: _18_5_1_3880181_1505050917522_312313_59359 */
                                }
                                part 'shared Processor and Memory' : OfficialCSRM::'Data'::'01 - CubeSat System Reference Model'::'5 - Architecture'::'L4_Components'::'L4.1_CubeSat Subsystems Components'::'L4.1.0_Shared Components'::'L4.1.0.2_Structures'::'Shared Processor and Memory' {
                                    doc /* Source XMI: _18_5_1_3880181_1505050927070_846277_59390
                                    Stereotype PartProperty
                                    UML aggregation: composite
                                    UML association: _18_5_1_3880181_1505050927070_389605_59389 */
                                }
                            }
                            connection def association_11 {
                                doc /* Source XMI: _18_5_1_3880181_1504966144184_939766_60690
                                UML end details are in the source map (SysML v2 connector ends have fixed [1..1] multiplicity). */
                                end end1 : OfficialCSRM::'Data'::'01 - CubeSat System Reference Model'::'5 - Architecture'::'L4_Components'::'L4.1_CubeSat Subsystems Components'::'L4.1.1_Mission Payload Components'::'L4.1.1.2_Structures'::'Instrument' {
                                    doc /* Source XMI: _18_5_1_3880181_1504966144184_867900_60691
                                    Stereotype PartProperty
                                    UML end name: instrument */
                                }
                                end end2 : OfficialCSRM::'Data'::'01 - CubeSat System Reference Model'::'5 - Architecture'::'L3_Subsystems'::'L3.1_CubeSat Subsystems'::'L3.1.2_Structures'::'Mission Payload' {
                                    doc /* Source XMI: _18_5_1_3880181_1504966144184_26591_60692
                                    UML end name: (unnamed) */
                                }
                            }
                            connection def association_12 {
                                doc /* Source XMI: _18_5_1_3880181_1504966149576_514634_60721
                                UML end details are in the source map (SysML v2 connector ends have fixed [1..1] multiplicity). */
                                end end1 : OfficialCSRM::'Data'::'01 - CubeSat System Reference Model'::'5 - Architecture'::'L4_Components'::'L4.1_CubeSat Subsystems Components'::'L4.1.1_Mission Payload Components'::'L4.1.1.2_Structures'::'Processor and Memory' {
                                    doc /* Source XMI: _18_5_1_3880181_1504966149576_636083_60722
                                    Stereotype PartProperty
                                    UML end name: processor and Memory */
                                }
                                end end2 : OfficialCSRM::'Data'::'01 - CubeSat System Reference Model'::'5 - Architecture'::'L3_Subsystems'::'L3.1_CubeSat Subsystems'::'L3.1.2_Structures'::'Mission Payload' {
                                    doc /* Source XMI: _18_5_1_3880181_1504966149576_1450_60723
                                    UML end name: (unnamed) */
                                }
                            }
                            connection def association_13 {
                                doc /* Source XMI: _18_5_1_3880181_1505050866981_414434_59247
                                UML end details are in the source map (SysML v2 connector ends have fixed [1..1] multiplicity). */
                                end end1 : OfficialCSRM::'Data'::'01 - CubeSat System Reference Model'::'5 - Architecture'::'L4_Components'::'L4.1_CubeSat Subsystems Components'::'L4.1.5_Guidance Navigation and Control Components'::'L4.1.5.2_Structures'::'Accelerometer' {
                                    doc /* Source XMI: _18_5_1_3880181_1505050866981_110069_59248
                                    Stereotype PartProperty
                                    UML end name: accelerometer */
                                }
                                end end2 : OfficialCSRM::'Data'::'01 - CubeSat System Reference Model'::'5 - Architecture'::'L3_Subsystems'::'L3.1_CubeSat Subsystems'::'L3.1.2_Structures'::'Guidance Navigation and Control Subsystem' {
                                    doc /* Source XMI: _18_5_1_3880181_1505050866981_305020_59249
                                    UML end name: (unnamed) */
                                }
                            }
                            connection def association_14 {
                                doc /* Source XMI: _18_5_1_3880181_1505050875592_54683_59277
                                UML end details are in the source map (SysML v2 connector ends have fixed [1..1] multiplicity). */
                                end end1 : OfficialCSRM::'Data'::'01 - CubeSat System Reference Model'::'5 - Architecture'::'L4_Components'::'L4.1_CubeSat Subsystems Components'::'L4.1.5_Guidance Navigation and Control Components'::'L4.1.5.2_Structures'::'GNSS Receiver' {
                                    doc /* Source XMI: _18_5_1_3880181_1505050875592_443207_59278
                                    Stereotype PartProperty
                                    UML end name: gNSS Receiver */
                                }
                                end end2 : OfficialCSRM::'Data'::'01 - CubeSat System Reference Model'::'5 - Architecture'::'L3_Subsystems'::'L3.1_CubeSat Subsystems'::'L3.1.2_Structures'::'Guidance Navigation and Control Subsystem' {
                                    doc /* Source XMI: _18_5_1_3880181_1505050875592_306842_59279
                                    UML end name: (unnamed) */
                                }
                            }
                            connection def association_15 {
                                doc /* Source XMI: _18_5_1_3880181_1505050917522_312313_59359
                                UML end details are in the source map (SysML v2 connector ends have fixed [1..1] multiplicity). */
                                end end1 : OfficialCSRM::'Data'::'01 - CubeSat System Reference Model'::'5 - Architecture'::'L4_Components'::'L4.1_CubeSat Subsystems Components'::'L4.1.5_Guidance Navigation and Control Components'::'L4.1.5.2_Structures'::'Software' {
                                    doc /* Source XMI: _18_5_1_3880181_1505050917522_656849_59360
                                    Stereotype PartProperty
                                    UML end name: software */
                                }
                                end end2 : OfficialCSRM::'Data'::'01 - CubeSat System Reference Model'::'5 - Architecture'::'L3_Subsystems'::'L3.1_CubeSat Subsystems'::'L3.1.2_Structures'::'Guidance Navigation and Control Subsystem' {
                                    doc /* Source XMI: _18_5_1_3880181_1505050917522_539080_59361
                                    UML end name: (unnamed) */
                                }
                            }
                            connection def association_16 {
                                doc /* Source XMI: _18_5_1_3880181_1505050927070_389605_59389
                                UML end details are in the source map (SysML v2 connector ends have fixed [1..1] multiplicity). */
                                end end1 : OfficialCSRM::'Data'::'01 - CubeSat System Reference Model'::'5 - Architecture'::'L4_Components'::'L4.1_CubeSat Subsystems Components'::'L4.1.0_Shared Components'::'L4.1.0.2_Structures'::'Shared Processor and Memory' {
                                    doc /* Source XMI: _18_5_1_3880181_1505050927070_846277_59390
                                    Stereotype PartProperty
                                    UML end name: shared Processor and Memory */
                                }
                                end end2 : OfficialCSRM::'Data'::'01 - CubeSat System Reference Model'::'5 - Architecture'::'L3_Subsystems'::'L3.1_CubeSat Subsystems'::'L3.1.2_Structures'::'Guidance Navigation and Control Subsystem' {
                                    doc /* Source XMI: _18_5_1_3880181_1505050927070_941559_59391
                                    UML end name: (unnamed) */
                                }
                            }
                            connection def association_17 {
                                doc /* Source XMI: _18_5_1_3880181_1505051904776_311150_59467
                                UML end details are in the source map (SysML v2 connector ends have fixed [1..1] multiplicity). */
                                end end1 : OfficialCSRM::'Data'::'01 - CubeSat System Reference Model'::'5 - Architecture'::'L4_Components'::'L4.1_CubeSat Subsystems Components'::'L4.1.4_Attitude Determination and Control Components'::'L4.1.4.2_Structures'::'Software' {
                                    doc /* Source XMI: _18_5_1_3880181_1505051904776_715917_59468
                                    Stereotype PartProperty
                                    UML end name: software */
                                }
                                end end2 : OfficialCSRM::'Data'::'01 - CubeSat System Reference Model'::'5 - Architecture'::'L3_Subsystems'::'L3.1_CubeSat Subsystems'::'L3.1.2_Structures'::'Attitude Determination and Control Subsystem' {
                                    doc /* Source XMI: _18_5_1_3880181_1505051904776_105354_59469
                                    UML end name: (unnamed) */
                                }
                            }
                            connection def association_18 {
                                doc /* Source XMI: _18_5_1_3880181_1505051910340_225127_59497
                                UML end details are in the source map (SysML v2 connector ends have fixed [1..1] multiplicity). */
                                end end1 : OfficialCSRM::'Data'::'01 - CubeSat System Reference Model'::'5 - Architecture'::'L4_Components'::'L4.1_CubeSat Subsystems Components'::'L4.1.4_Attitude Determination and Control Components'::'L4.1.4.2_Structures'::'Actuator' {
                                    doc /* Source XMI: _18_5_1_3880181_1505051910340_912233_59498
                                    Stereotype PartProperty
                                    UML end name: actuator */
                                }
                                end end2 : OfficialCSRM::'Data'::'01 - CubeSat System Reference Model'::'5 - Architecture'::'L3_Subsystems'::'L3.1_CubeSat Subsystems'::'L3.1.2_Structures'::'Attitude Determination and Control Subsystem' {
                                    doc /* Source XMI: _18_5_1_3880181_1505051910340_664147_59499
                                    UML end name: (unnamed) */
                                }
                            }
                            connection def association_19 {
                                doc /* Source XMI: _18_5_1_3880181_1505051918826_920978_59527
                                UML end details are in the source map (SysML v2 connector ends have fixed [1..1] multiplicity). */
                                end end1 : OfficialCSRM::'Data'::'01 - CubeSat System Reference Model'::'5 - Architecture'::'L4_Components'::'L4.1_CubeSat Subsystems Components'::'L4.1.4_Attitude Determination and Control Components'::'L4.1.4.2_Structures'::'Sensor' {
                                    doc /* Source XMI: _18_5_1_3880181_1505051918826_844900_59528
                                    Stereotype PartProperty
                                    UML end name: sensor */
                                }
                                end end2 : OfficialCSRM::'Data'::'01 - CubeSat System Reference Model'::'5 - Architecture'::'L3_Subsystems'::'L3.1_CubeSat Subsystems'::'L3.1.2_Structures'::'Attitude Determination and Control Subsystem' {
                                    doc /* Source XMI: _18_5_1_3880181_1505051918826_904605_59529
                                    UML end name: (unnamed) */
                                }
                            }
                            connection def association_20 {
                                doc /* Source XMI: _18_5_1_3880181_1505051926390_546978_59557
                                UML end details are in the source map (SysML v2 connector ends have fixed [1..1] multiplicity). */
                                end end1 : OfficialCSRM::'Data'::'01 - CubeSat System Reference Model'::'5 - Architecture'::'L4_Components'::'L4.1_CubeSat Subsystems Components'::'L4.1.0_Shared Components'::'L4.1.0.2_Structures'::'Shared Processor and Memory' {
                                    doc /* Source XMI: _18_5_1_3880181_1505051926390_570536_59558
                                    Stereotype PartProperty
                                    UML end name: shared Processor and Memory */
                                }
                                end end2 : OfficialCSRM::'Data'::'01 - CubeSat System Reference Model'::'5 - Architecture'::'L3_Subsystems'::'L3.1_CubeSat Subsystems'::'L3.1.2_Structures'::'Attitude Determination and Control Subsystem' {
                                    doc /* Source XMI: _18_5_1_3880181_1505051926390_158300_59559
                                    UML end name: (unnamed) */
                                }
                            }
                            connection def association_21 {
                                doc /* Source XMI: _18_5_1_3880181_1505052868446_387484_59875
                                UML end details are in the source map (SysML v2 connector ends have fixed [1..1] multiplicity). */
                                end end1 : OfficialCSRM::'Data'::'01 - CubeSat System Reference Model'::'5 - Architecture'::'L4_Components'::'L4.1_CubeSat Subsystems Components'::'L4.1.2_Command and Data Handling Components'::'L4.1.2.2_Structures'::'Command, Telemetry, and Data Bus' {
                                    doc /* Source XMI: _18_5_1_3880181_1505052868446_280959_59876
                                    Stereotype PartProperty
                                    UML end name: (unnamed) */
                                }
                                end end2 : OfficialCSRM::'Data'::'01 - CubeSat System Reference Model'::'5 - Architecture'::'L3_Subsystems'::'L3.1_CubeSat Subsystems'::'L3.1.2_Structures'::'Command and Data Handling Subsystem' {
                                    doc /* Source XMI: _18_5_1_3880181_1505052868446_289307_59877
                                    UML end name: (unnamed) */
                                }
                            }
                            connection def association_22 {
                                doc /* Source XMI: _18_5_1_3880181_1505052908719_121393_59955
                                UML end details are in the source map (SysML v2 connector ends have fixed [1..1] multiplicity). */
                                end end1 : OfficialCSRM::'Data'::'01 - CubeSat System Reference Model'::'5 - Architecture'::'L4_Components'::'L4.1_CubeSat Subsystems Components'::'L4.1.2_Command and Data Handling Components'::'L4.1.2.2_Structures'::'Processor and Memory' {
                                    doc /* Source XMI: _18_5_1_3880181_1505052908719_471437_59956
                                    Stereotype PartProperty
                                    UML end name: processor and Memory */
                                }
                                end end2 : OfficialCSRM::'Data'::'01 - CubeSat System Reference Model'::'5 - Architecture'::'L3_Subsystems'::'L3.1_CubeSat Subsystems'::'L3.1.2_Structures'::'Command and Data Handling Subsystem' {
                                    doc /* Source XMI: _18_5_1_3880181_1505052908719_908701_59957
                                    UML end name: (unnamed) */
                                }
                            }
                            connection def association_23 {
                                doc /* Source XMI: _18_5_1_3880181_1505054228737_659474_60390
                                UML end details are in the source map (SysML v2 connector ends have fixed [1..1] multiplicity). */
                                end end1 : OfficialCSRM::'Data'::'01 - CubeSat System Reference Model'::'5 - Architecture'::'L4_Components'::'L4.1_CubeSat Subsystems Components'::'L4.1.3_Communication Components'::'L4.1.3.2_Structures'::'Processor and Memory' {
                                    doc /* Source XMI: _18_5_1_3880181_1505054228737_235187_60391
                                    Stereotype PartProperty
                                    UML end name: processor and Memory */
                                }
                                end end2 : OfficialCSRM::'Data'::'01 - CubeSat System Reference Model'::'5 - Architecture'::'L3_Subsystems'::'L3.1_CubeSat Subsystems'::'L3.1.2_Structures'::'Communication Subsystem' {
                                    doc /* Source XMI: _18_5_1_3880181_1505054228737_855442_60392
                                    UML end name: (unnamed) */
                                }
                            }
                            connection def association_24 {
                                doc /* Source XMI: _18_5_1_3880181_1505054238693_239871_60420
                                UML end details are in the source map (SysML v2 connector ends have fixed [1..1] multiplicity). */
                                end end1 : OfficialCSRM::'Data'::'01 - CubeSat System Reference Model'::'5 - Architecture'::'L4_Components'::'L4.1_CubeSat Subsystems Components'::'L4.1.3_Communication Components'::'L4.1.3.2_Structures'::'Receive Antenna and Equipment' {
                                    doc /* Source XMI: _18_5_1_3880181_1505054238693_563290_60421
                                    Stereotype PartProperty
                                    UML end name: receive Antenna and Equipment */
                                }
                                end end2 : OfficialCSRM::'Data'::'01 - CubeSat System Reference Model'::'5 - Architecture'::'L3_Subsystems'::'L3.1_CubeSat Subsystems'::'L3.1.2_Structures'::'Communication Subsystem' {
                                    doc /* Source XMI: _18_5_1_3880181_1505054238693_895464_60422
                                    UML end name: (unnamed) */
                                }
                            }
                            connection def association_25 {
                                doc /* Source XMI: _18_5_1_3880181_1505054264245_975433_60502
                                UML end details are in the source map (SysML v2 connector ends have fixed [1..1] multiplicity). */
                                end end1 : OfficialCSRM::'Data'::'01 - CubeSat System Reference Model'::'5 - Architecture'::'L4_Components'::'L4.1_CubeSat Subsystems Components'::'L4.1.3_Communication Components'::'L4.1.3.2_Structures'::'Transmit Antenna and Equipment' {
                                    doc /* Source XMI: _18_5_1_3880181_1505054264245_356300_60503
                                    Stereotype PartProperty
                                    UML end name: transmit Antenna and Equipment */
                                }
                                end end2 : OfficialCSRM::'Data'::'01 - CubeSat System Reference Model'::'5 - Architecture'::'L3_Subsystems'::'L3.1_CubeSat Subsystems'::'L3.1.2_Structures'::'Communication Subsystem' {
                                    doc /* Source XMI: _18_5_1_3880181_1505054264245_435737_60504
                                    UML end name: (unnamed) */
                                }
                            }
                            connection def association_26 {
                                doc /* Source XMI: _18_5_1_3880181_1505055429243_905410_61105
                                UML end details are in the source map (SysML v2 connector ends have fixed [1..1] multiplicity). */
                                end end1 : OfficialCSRM::'Data'::'01 - CubeSat System Reference Model'::'5 - Architecture'::'L4_Components'::'L4.1_CubeSat Subsystems Components'::'L4.1.7_Power Components'::'L4.1.7.2_Structures'::'Batteries' {
                                    doc /* Source XMI: _18_5_1_3880181_1505055429243_836355_61106
                                    Stereotype PartProperty
                                    UML end name: batteries */
                                }
                                end end2 : OfficialCSRM::'Data'::'01 - CubeSat System Reference Model'::'5 - Architecture'::'L3_Subsystems'::'L3.1_CubeSat Subsystems'::'L3.1.2_Structures'::'Power Subsystem' {
                                    doc /* Source XMI: _18_5_1_3880181_1505055429243_71892_61107
                                    UML end name: (unnamed) */
                                }
                            }
                            connection def association_27 {
                                doc /* Source XMI: _18_5_1_3880181_1505055437901_681839_61135
                                UML end details are in the source map (SysML v2 connector ends have fixed [1..1] multiplicity). */
                                end end1 : OfficialCSRM::'Data'::'01 - CubeSat System Reference Model'::'5 - Architecture'::'L4_Components'::'L4.1_CubeSat Subsystems Components'::'L4.1.7_Power Components'::'L4.1.7.2_Structures'::'Regulators and Converters' {
                                    doc /* Source XMI: _18_5_1_3880181_1505055437901_455231_61136
                                    Stereotype PartProperty
                                    UML end name: regulators and Converters */
                                }
                                end end2 : OfficialCSRM::'Data'::'01 - CubeSat System Reference Model'::'5 - Architecture'::'L3_Subsystems'::'L3.1_CubeSat Subsystems'::'L3.1.2_Structures'::'Power Subsystem' {
                                    doc /* Source XMI: _18_5_1_3880181_1505055437901_720607_61137
                                    UML end name: (unnamed) */
                                }
                            }
                            connection def association_28 {
                                doc /* Source XMI: _18_5_1_3880181_1505055446934_975434_61165
                                UML end details are in the source map (SysML v2 connector ends have fixed [1..1] multiplicity). */
                                end end1 : OfficialCSRM::'Data'::'01 - CubeSat System Reference Model'::'5 - Architecture'::'L4_Components'::'L4.1_CubeSat Subsystems Components'::'L4.1.7_Power Components'::'L4.1.7.2_Structures'::'Solar Arrays' {
                                    doc /* Source XMI: _18_5_1_3880181_1505055446934_155733_61166
                                    Stereotype PartProperty
                                    UML end name: solar Arrays */
                                }
                                end end2 : OfficialCSRM::'Data'::'01 - CubeSat System Reference Model'::'5 - Architecture'::'L3_Subsystems'::'L3.1_CubeSat Subsystems'::'L3.1.2_Structures'::'Power Subsystem' {
                                    doc /* Source XMI: _18_5_1_3880181_1505055446934_171461_61167
                                    UML end name: (unnamed) */
                                }
                            }
                            connection def association_29 {
                                doc /* Source XMI: _18_5_1_3880181_1505055483722_375264_61247
                                UML end details are in the source map (SysML v2 connector ends have fixed [1..1] multiplicity). */
                                end end1 : OfficialCSRM::'Data'::'01 - CubeSat System Reference Model'::'5 - Architecture'::'L4_Components'::'L4.1_CubeSat Subsystems Components'::'L4.1.7_Power Components'::'L4.1.7.2_Structures'::'Power Circuits and Switches' {
                                    doc /* Source XMI: _18_5_1_3880181_1505055483722_439147_61248
                                    Stereotype PartProperty
                                    UML end name: power Circuits and Switches */
                                }
                                end end2 : OfficialCSRM::'Data'::'01 - CubeSat System Reference Model'::'5 - Architecture'::'L3_Subsystems'::'L3.1_CubeSat Subsystems'::'L3.1.2_Structures'::'Power Subsystem' {
                                    doc /* Source XMI: _18_5_1_3880181_1505055483722_800323_61249
                                    UML end name: (unnamed) */
                                }
                            }
                            connection def association_30 {
                                doc /* Source XMI: _18_5_1_3880181_1505055492849_804272_61277
                                UML end details are in the source map (SysML v2 connector ends have fixed [1..1] multiplicity). */
                                end end1 : OfficialCSRM::'Data'::'01 - CubeSat System Reference Model'::'5 - Architecture'::'L4_Components'::'L4.1_CubeSat Subsystems Components'::'L4.1.7_Power Components'::'L4.1.7.2_Structures'::'Processor and Memory' {
                                    doc /* Source XMI: _18_5_1_3880181_1505055492849_150646_61278
                                    Stereotype PartProperty
                                    UML end name: processor and Memory */
                                }
                                end end2 : OfficialCSRM::'Data'::'01 - CubeSat System Reference Model'::'5 - Architecture'::'L3_Subsystems'::'L3.1_CubeSat Subsystems'::'L3.1.2_Structures'::'Power Subsystem' {
                                    doc /* Source XMI: _18_5_1_3880181_1505055492849_648963_61279
                                    UML end name: (unnamed) */
                                }
                            }
                            connection def association_31 {
                                doc /* Source XMI: _18_5_1_3880181_1505055502585_848240_61307
                                UML end details are in the source map (SysML v2 connector ends have fixed [1..1] multiplicity). */
                                end end1 : OfficialCSRM::'Data'::'01 - CubeSat System Reference Model'::'5 - Architecture'::'L4_Components'::'L4.1_CubeSat Subsystems Components'::'L4.1.7_Power Components'::'L4.1.7.2_Structures'::'Software' {
                                    doc /* Source XMI: _18_5_1_3880181_1505055502585_243540_61308
                                    Stereotype PartProperty
                                    UML end name: software */
                                }
                                end end2 : OfficialCSRM::'Data'::'01 - CubeSat System Reference Model'::'5 - Architecture'::'L3_Subsystems'::'L3.1_CubeSat Subsystems'::'L3.1.2_Structures'::'Power Subsystem' {
                                    doc /* Source XMI: _18_5_1_3880181_1505055502585_446450_61309
                                    UML end name: (unnamed) */
                                }
                            }
                            connection def association_32 {
                                doc /* Source XMI: _18_5_1_3880181_1505056214765_993952_62114
                                UML end details are in the source map (SysML v2 connector ends have fixed [1..1] multiplicity). */
                                end end1 : OfficialCSRM::'Data'::'01 - CubeSat System Reference Model'::'5 - Architecture'::'L4_Components'::'L4.1_CubeSat Subsystems Components'::'L4.1.9_Propulsion Components'::'L4.1.9.2_Structures'::'Propellant Storage' {
                                    doc /* Source XMI: _18_5_1_3880181_1505056214765_70129_62115
                                    Stereotype PartProperty
                                    UML end name: propellant Storage */
                                }
                                end end2 : OfficialCSRM::'Data'::'01 - CubeSat System Reference Model'::'5 - Architecture'::'L3_Subsystems'::'L3.1_CubeSat Subsystems'::'L3.1.2_Structures'::'Propulsion Subsystem' {
                                    doc /* Source XMI: _18_5_1_3880181_1505056214765_302341_62116
                                    UML end name: (unnamed) */
                                }
                            }
                            connection def association_33 {
                                doc /* Source XMI: _18_5_1_3880181_1505056226158_342495_62144
                                UML end details are in the source map (SysML v2 connector ends have fixed [1..1] multiplicity). */
                                end end1 : OfficialCSRM::'Data'::'01 - CubeSat System Reference Model'::'5 - Architecture'::'L4_Components'::'L4.1_CubeSat Subsystems Components'::'L4.1.9_Propulsion Components'::'L4.1.9.2_Structures'::'Propellant Control' {
                                    doc /* Source XMI: _18_5_1_3880181_1505056226158_314629_62145
                                    Stereotype PartProperty
                                    UML end name: propellant Control */
                                }
                                end end2 : OfficialCSRM::'Data'::'01 - CubeSat System Reference Model'::'5 - Architecture'::'L3_Subsystems'::'L3.1_CubeSat Subsystems'::'L3.1.2_Structures'::'Propulsion Subsystem' {
                                    doc /* Source XMI: _18_5_1_3880181_1505056226158_148690_62146
                                    UML end name: (unnamed) */
                                }
                            }
                            connection def association_34 {
                                doc /* Source XMI: _18_5_1_3880181_1505056233128_424942_62174
                                UML end details are in the source map (SysML v2 connector ends have fixed [1..1] multiplicity). */
                                end end1 : OfficialCSRM::'Data'::'01 - CubeSat System Reference Model'::'5 - Architecture'::'L4_Components'::'L4.1_CubeSat Subsystems Components'::'L4.1.9_Propulsion Components'::'L4.1.9.2_Structures'::'Thrusters' {
                                    doc /* Source XMI: _18_5_1_3880181_1505056233128_193505_62175
                                    Stereotype PartProperty
                                    UML end name: thrusters */
                                }
                                end end2 : OfficialCSRM::'Data'::'01 - CubeSat System Reference Model'::'5 - Architecture'::'L3_Subsystems'::'L3.1_CubeSat Subsystems'::'L3.1.2_Structures'::'Propulsion Subsystem' {
                                    doc /* Source XMI: _18_5_1_3880181_1505056233128_410321_62176
                                    UML end name: (unnamed) */
                                }
                            }
                            connection def association_35 {
                                doc /* Source XMI: _18_5_1_3880181_1505056241864_595199_62204
                                UML end details are in the source map (SysML v2 connector ends have fixed [1..1] multiplicity). */
                                end end1 : OfficialCSRM::'Data'::'01 - CubeSat System Reference Model'::'5 - Architecture'::'L4_Components'::'L4.1_CubeSat Subsystems Components'::'L4.1.9_Propulsion Components'::'L4.1.9.2_Structures'::'Processor and Memory' {
                                    doc /* Source XMI: _18_5_1_3880181_1505056241864_709528_62205
                                    Stereotype PartProperty
                                    UML end name: processor and Memory */
                                }
                                end end2 : OfficialCSRM::'Data'::'01 - CubeSat System Reference Model'::'5 - Architecture'::'L3_Subsystems'::'L3.1_CubeSat Subsystems'::'L3.1.2_Structures'::'Propulsion Subsystem' {
                                    doc /* Source XMI: _18_5_1_3880181_1505056241864_193816_62206
                                    UML end name: (unnamed) */
                                }
                            }
                            connection def association_36 {
                                doc /* Source XMI: _18_5_1_3880181_1505056252584_577106_62234
                                UML end details are in the source map (SysML v2 connector ends have fixed [1..1] multiplicity). */
                                end end1 : OfficialCSRM::'Data'::'01 - CubeSat System Reference Model'::'5 - Architecture'::'L4_Components'::'L4.1_CubeSat Subsystems Components'::'L4.1.9_Propulsion Components'::'L4.1.9.2_Structures'::'Software' {
                                    doc /* Source XMI: _18_5_1_3880181_1505056252600_224208_62235
                                    Stereotype PartProperty
                                    UML end name: software */
                                }
                                end end2 : OfficialCSRM::'Data'::'01 - CubeSat System Reference Model'::'5 - Architecture'::'L3_Subsystems'::'L3.1_CubeSat Subsystems'::'L3.1.2_Structures'::'Propulsion Subsystem' {
                                    doc /* Source XMI: _18_5_1_3880181_1505056252600_502258_62236
                                    UML end name: (unnamed) */
                                }
                            }
                            connection def association_37 {
                                doc /* Source XMI: _18_5_1_3880181_1505056658220_929903_62552
                                UML end details are in the source map (SysML v2 connector ends have fixed [1..1] multiplicity). */
                                end end1 : OfficialCSRM::'Data'::'01 - CubeSat System Reference Model'::'5 - Architecture'::'L4_Components'::'L4.1_CubeSat Subsystems Components'::'L4.1.6_Structures and Mechanisms Components'::'L4.1.6.2_Structures'::'Actuated Mount' {
                                    doc /* Source XMI: _18_5_1_3880181_1505056658220_33051_62553
                                    Stereotype PartProperty
                                    UML end name: actuated Mount */
                                }
                                end end2 : OfficialCSRM::'Data'::'01 - CubeSat System Reference Model'::'5 - Architecture'::'L3_Subsystems'::'L3.1_CubeSat Subsystems'::'L3.1.2_Structures'::'Structures and Mechanisms Subsystem' {
                                    doc /* Source XMI: _18_5_1_3880181_1505056658220_245426_62554
                                    UML end name: (unnamed) */
                                }
                            }
                            connection def association_38 {
                                doc /* Source XMI: _18_5_1_3880181_1505056669175_130656_62582
                                UML end details are in the source map (SysML v2 connector ends have fixed [1..1] multiplicity). */
                                end end1 : OfficialCSRM::'Data'::'01 - CubeSat System Reference Model'::'5 - Architecture'::'L4_Components'::'L4.1_CubeSat Subsystems Components'::'L4.1.6_Structures and Mechanisms Components'::'L4.1.6.2_Structures'::'Deployable Mount' {
                                    doc /* Source XMI: _18_5_1_3880181_1505056669175_349972_62583
                                    Stereotype PartProperty
                                    UML end name: deployable Mount */
                                }
                                end end2 : OfficialCSRM::'Data'::'01 - CubeSat System Reference Model'::'5 - Architecture'::'L3_Subsystems'::'L3.1_CubeSat Subsystems'::'L3.1.2_Structures'::'Structures and Mechanisms Subsystem' {
                                    doc /* Source XMI: _18_5_1_3880181_1505056669175_416694_62584
                                    UML end name: (unnamed) */
                                }
                            }
                            connection def association_39 {
                                doc /* Source XMI: _18_5_1_3880181_1505056677364_572191_62612
                                UML end details are in the source map (SysML v2 connector ends have fixed [1..1] multiplicity). */
                                end end1 : OfficialCSRM::'Data'::'01 - CubeSat System Reference Model'::'5 - Architecture'::'L4_Components'::'L4.1_CubeSat Subsystems Components'::'L4.1.6_Structures and Mechanisms Components'::'L4.1.6.2_Structures'::'Static Mount' {
                                    doc /* Source XMI: _18_5_1_3880181_1505056677364_646061_62613
                                    Stereotype PartProperty
                                    UML end name: static Mount */
                                }
                                end end2 : OfficialCSRM::'Data'::'01 - CubeSat System Reference Model'::'5 - Architecture'::'L3_Subsystems'::'L3.1_CubeSat Subsystems'::'L3.1.2_Structures'::'Structures and Mechanisms Subsystem' {
                                    doc /* Source XMI: _18_5_1_3880181_1505056677379_529070_62614
                                    UML end name: (unnamed) */
                                }
                            }
                            connection def association_40 {
                                doc /* Source XMI: _18_5_1_3880181_1505057858385_74662_62957
                                UML end details are in the source map (SysML v2 connector ends have fixed [1..1] multiplicity). */
                                end end1 : OfficialCSRM::'Data'::'01 - CubeSat System Reference Model'::'5 - Architecture'::'L4_Components'::'L4.1_CubeSat Subsystems Components'::'L4.1.8_Thermal Components'::'L4.1.8.2_Structures'::'Thermal Sensors, Sources, and Sinks' {
                                    doc /* Source XMI: _18_5_1_3880181_1505057858385_254941_62958
                                    Stereotype PartProperty
                                    UML end name: (unnamed) */
                                }
                                end end2 : OfficialCSRM::'Data'::'01 - CubeSat System Reference Model'::'5 - Architecture'::'L3_Subsystems'::'L3.1_CubeSat Subsystems'::'L3.1.2_Structures'::'Thermal Subsystem' {
                                    doc /* Source XMI: _18_5_1_3880181_1505057858385_147296_62959
                                    UML end name: (unnamed) */
                                }
                            }
                            connection def association_41 {
                                doc /* Source XMI: _18_5_1_3880181_1505057879514_545440_62985
                                UML end details are in the source map (SysML v2 connector ends have fixed [1..1] multiplicity). */
                                end end1 : OfficialCSRM::'Data'::'01 - CubeSat System Reference Model'::'5 - Architecture'::'L4_Components'::'L4.1_CubeSat Subsystems Components'::'L4.1.8_Thermal Components'::'L4.1.8.2_Structures'::'Processor and Memory' {
                                    doc /* Source XMI: _18_5_1_3880181_1505057879514_227931_62986
                                    Stereotype PartProperty
                                    UML end name: processor and Memory */
                                }
                                end end2 : OfficialCSRM::'Data'::'01 - CubeSat System Reference Model'::'5 - Architecture'::'L3_Subsystems'::'L3.1_CubeSat Subsystems'::'L3.1.2_Structures'::'Thermal Subsystem' {
                                    doc /* Source XMI: _18_5_1_3880181_1505057879514_991926_62987
                                    UML end name: (unnamed) */
                                }
                            }
                            connection def association_42 {
                                doc /* Source XMI: _18_5_1_3880181_1505057887250_935444_63015
                                UML end details are in the source map (SysML v2 connector ends have fixed [1..1] multiplicity). */
                                end end1 : OfficialCSRM::'Data'::'01 - CubeSat System Reference Model'::'5 - Architecture'::'L4_Components'::'L4.1_CubeSat Subsystems Components'::'L4.1.8_Thermal Components'::'L4.1.8.2_Structures'::'Software' {
                                    doc /* Source XMI: _18_5_1_3880181_1505057887250_36678_63016
                                    Stereotype PartProperty
                                    UML end name: software */
                                }
                                end end2 : OfficialCSRM::'Data'::'01 - CubeSat System Reference Model'::'5 - Architecture'::'L3_Subsystems'::'L3.1_CubeSat Subsystems'::'L3.1.2_Structures'::'Thermal Subsystem' {
                                    doc /* Source XMI: _18_5_1_3880181_1505057887250_735425_63017
                                    UML end name: (unnamed) */
                                }
                            }
                            part def 'Mission Payload' {
                                doc /* Source XMI: _18_0_6_3e4019a_1472151609453_690849_15836
                                Stereotype Subsystem
                                UML kind: uml:Class */
                                // UML generalization _18_4_1_3880181_1492191352165_847102_45864 to MD_customization_for_SysML.mdzip#_18_3_903028d_1448291312269_537593_13833
                                part 'instrument' : OfficialCSRM::'Data'::'01 - CubeSat System Reference Model'::'5 - Architecture'::'L4_Components'::'L4.1_CubeSat Subsystems Components'::'L4.1.1_Mission Payload Components'::'L4.1.1.2_Structures'::'Instrument' {
                                    doc /* Source XMI: _18_5_1_3880181_1504966144184_867900_60691
                                    Stereotype PartProperty
                                    UML aggregation: composite
                                    UML association: _18_5_1_3880181_1504966144184_939766_60690 */
                                }
                                part 'processor and Memory' : OfficialCSRM::'Data'::'01 - CubeSat System Reference Model'::'5 - Architecture'::'L4_Components'::'L4.1_CubeSat Subsystems Components'::'L4.1.1_Mission Payload Components'::'L4.1.1.2_Structures'::'Processor and Memory' {
                                    doc /* Source XMI: _18_5_1_3880181_1504966149576_636083_60722
                                    Stereotype PartProperty
                                    UML aggregation: composite
                                    UML association: _18_5_1_3880181_1504966149576_514634_60721 */
                                }
                            }
                        }
                        package 'L3.1.1_Behaviors' {
                            doc /* Source XMI: _18_0_6_3e4019a_1472151563833_941202_14087
                            Comment _19_0_2_3880181_1600893326399_714549_62881
                            The package of CubeSat subsystems behaviors, use cases, and activities.  To be populated by a mission specific team.
                            UML kind: uml:Package */
                            package 'L3.1.1.1_CubeSat Subsystems Behaviors' {
                                doc /* Source XMI: _19_0_2_3880181_1562511536275_924441_62265
                                Comment _19_0_2_3880181_1600892781943_112776_62878
                                The repository for CubeSat subsystems behaviors.  To be populated by a mission-specific team.
                                UML kind: uml:Package */
                                package 'CubeSat Subsystem Behavior A' {
                                    doc /* Source XMI: _19_0_2_3880181_1572630578440_875806_64455
                                    Comment _19_0_2_3880181_1601215774568_917820_62979
                                    Example / placeholder / template for CubeSat Subsystems Behaviors
                                    UML kind: uml:Package */
                                    dependency relationship_1 from OfficialCSRM::'Data'::'01 - CubeSat System Reference Model'::'5 - Architecture'::'L3_Subsystems'::'L3.1_CubeSat Subsystems'::'L3.1.1_Behaviors'::'L3.1.1.1_CubeSat Subsystems Behaviors'::'CubeSat Subsystem Behavior A' to OfficialCSRM::'Data'::'01 - CubeSat System Reference Model'::'4 - Requirements'::'L3 Subsystem Rqts'::'L3.1 CubeSat Subsystems Rqts'::'L3.1.1 Mission Payload Rqts'::'Mission Payload Rqts Group'::'Requirement Name' {
                                        doc /* Source XMI: _19_0_2_3880181_1637008383888_992524_56988
                                        Stereotype Refine
                                        UML kind: uml:Abstraction */
                                    }
                                }
                            }
                            package 'L3.1.1.3_CubeSat Subsystems Activities' {
                                doc /* Source XMI: _19_0_2_3880181_1570470539019_198532_63149
                                Comment _19_0_2_3880181_1600893056633_129452_62880
                                The repository for CubeSat subsystems activities.  To be populated by a mission-specific team.
                                UML kind: uml:Package */
                                package 'CubeSat Subsystem Activity A' {
                                    doc /* Source XMI: _19_0_2_3880181_1572630149590_119144_64395
                                    Comment _19_0_2_3880181_1601215931146_207610_62983
                                    Example / placeholder / template for CubeSat Subsystems Activities
                                    UML kind: uml:Package */
                                    dependency relationship_1 from OfficialCSRM::'Data'::'01 - CubeSat System Reference Model'::'5 - Architecture'::'L3_Subsystems'::'L3.1_CubeSat Subsystems'::'L3.1.1_Behaviors'::'L3.1.1.3_CubeSat Subsystems Activities'::'CubeSat Subsystem Activity A' to OfficialCSRM::'Data'::'01 - CubeSat System Reference Model'::'5 - Architecture'::'L3_Subsystems'::'L3.1_CubeSat Subsystems'::'L3.1.1_Behaviors'::'L3.1.1.2_CubeSat Subsystems Use Cases'::'CubeSat Subsystem Use Case A' {
                                        doc /* Source XMI: _19_0_2_3880181_1572639824308_263929_63479
                                        Stereotype Refine
                                        UML kind: uml:Abstraction */
                                    }
                                    action def 'CubeSat Subsystem Activity A' {
                                        doc /* Source XMI: _19_0_2_3880181_1637009692970_174288_57040
                                        UML kind: uml:Activity */
                                    }
                                }
                            }
                            package 'L3.1.1.2_CubeSat Subsystems Use Cases' {
                                doc /* Source XMI: _19_0_2_3880181_1570470617138_247152_63150
                                Comment _19_0_2_3880181_1600892990469_849145_62879
                                The repository for CubeSat subsystems use cases.  To be populated by a mission-specific team.
                                UML kind: uml:Package */
                                package 'CubeSat Subsystem Use Case A' {
                                    doc /* Source XMI: _19_0_2_3880181_1572630757017_969529_64515
                                    Comment _19_0_2_3880181_1601215859909_864763_62981
                                    Example / placeholder / template for CubeSat Subsystems Use Cases
                                    UML kind: uml:Package */
                                    dependency relationship_1 from OfficialCSRM::'Data'::'01 - CubeSat System Reference Model'::'5 - Architecture'::'L3_Subsystems'::'L3.1_CubeSat Subsystems'::'L3.1.1_Behaviors'::'L3.1.1.2_CubeSat Subsystems Use Cases'::'CubeSat Subsystem Use Case A' to OfficialCSRM::'Data'::'01 - CubeSat System Reference Model'::'5 - Architecture'::'L3_Subsystems'::'L3.1_CubeSat Subsystems'::'L3.1.1_Behaviors'::'L3.1.1.1_CubeSat Subsystems Behaviors'::'CubeSat Subsystem Behavior A' {
                                        doc /* Source XMI: _19_0_2_3880181_1637008620009_303023_56992
                                        Stereotype Refine
                                        UML kind: uml:Abstraction */
                                    }
                                }
                            }
                        }
                    }
                    package 'L3.2_Ground Subsystems' {
                        doc /* Source XMI: _18_0_6_3e4019a_1472151552168_986879_13485
                        Comment _19_0_2_3880181_1600957854577_24026_62601
                        The package of Ground subsystems behaviors and structures.
                        UML kind: uml:Package */
                        package 'L3.2.1_Behaviors' {
                            doc /* Source XMI: _18_0_6_3e4019a_1472151563830_686981_14081
                            Comment _19_0_2_3880181_1600959108184_909809_62780
                            The package of Ground subsystems behaviors, use cases, and activities.  To be populated by a mission specific team.
                            UML kind: uml:Package */
                            package 'L3.2.1.1_Ground Subsystems Behaviors' {
                                doc /* Source XMI: _19_0_2_3880181_1562511898621_90524_62338
                                Comment _19_0_2_3880181_1600959363971_158155_62781
                                The repository for Ground subsystems behaviors.  To be populated by a mission-specific team
                                UML kind: uml:Package */
                                package 'Ground Subsystems Behavior A' {
                                    doc /* Source XMI: _19_0_2_3880181_1572707829608_984170_63338
                                    Comment _19_0_2_3880181_1601216136911_453362_62986
                                    Example / placeholder / template for Ground Subsystems Behaviors
                                    UML kind: uml:Package */
                                    dependency relationship_1 from OfficialCSRM::'Data'::'01 - CubeSat System Reference Model'::'5 - Architecture'::'L3_Subsystems'::'L3.2_Ground Subsystems'::'L3.2.1_Behaviors'::'L3.2.1.1_Ground Subsystems Behaviors'::'Ground Subsystems Behavior A' to OfficialCSRM::'Data'::'01 - CubeSat System Reference Model'::'4 - Requirements'::'L3 Subsystem Rqts'::'L3.2 Ground Subsystems Rqts'::'L3.2.1 Plan and Schedule Subsystem Rqts'::'Plan and Schedule Subsystem Rqts Group'::'Plan and Schedule Requirement A' {
                                        doc /* Source XMI: _19_0_2_3880181_1637005006460_727276_55988
                                        Stereotype Refine
                                        UML kind: uml:Abstraction */
                                    }
                                }
                            }
                            package 'L3.2.1.3_Ground Subsystems Activities' {
                                doc /* Source XMI: _19_0_2_3880181_1570636957265_327502_62896
                                Comment _19_0_2_3880181_1600959523202_708774_62783
                                The repository for Ground subsystems activities.  To be populated by a mission-specific team
                                UML kind: uml:Package */
                                package 'Ground Subsystem Activity A' {
                                    doc /* Source XMI: _19_0_2_3880181_1572631724744_37157_64798
                                    Comment _19_0_2_3880181_1601216476483_536250_63000
                                    Example / placeholder / template for Ground Subsystems Activities.
                                    UML kind: uml:Package */
                                    action def 'Ground Subsystem Activity A' {
                                        doc /* Source XMI: _19_0_2_3880181_1637004502333_172286_55467
                                        UML kind: uml:Activity */
                                    }
                                    dependency relationship_2 from OfficialCSRM::'Data'::'01 - CubeSat System Reference Model'::'5 - Architecture'::'L3_Subsystems'::'L3.2_Ground Subsystems'::'L3.2.1_Behaviors'::'L3.2.1.3_Ground Subsystems Activities'::'Ground Subsystem Activity A' to OfficialCSRM::'Data'::'01 - CubeSat System Reference Model'::'5 - Architecture'::'L3_Subsystems'::'L3.2_Ground Subsystems'::'L3.2.1_Behaviors'::'L3.2.1.2_Ground Subsystems Use Cases'::'Ground Subsystem Use Case A' {
                                        doc /* Source XMI: _19_0_2_3880181_1637005348133_803629_55998
                                        Stereotype Refine
                                        UML kind: uml:Abstraction */
                                    }
                                }
                            }
                            package 'L3.2.1.2_Ground Subsystems Use Cases' {
                                doc /* Source XMI: _19_0_2_3880181_1570637091355_288821_62909
                                Comment _19_0_2_3880181_1600959457540_423998_62782
                                The repository for Ground subsystems use cases.  To be populated by a mission-specific team.
                                UML kind: uml:Package */
                                package 'Ground Subsystem Use Case A' {
                                    doc /* Source XMI: _19_0_2_3880181_1572631940673_4656_64916
                                    Comment _19_0_2_3880181_1601216342078_760828_62988
                                    Example / placeholder / template for Ground Subsystems Use Cases
                                    UML kind: uml:Package */
                                    dependency relationship_1 from OfficialCSRM::'Data'::'01 - CubeSat System Reference Model'::'5 - Architecture'::'L3_Subsystems'::'L3.2_Ground Subsystems'::'L3.2.1_Behaviors'::'L3.2.1.2_Ground Subsystems Use Cases'::'Ground Subsystem Use Case A' to OfficialCSRM::'Data'::'01 - CubeSat System Reference Model'::'5 - Architecture'::'L3_Subsystems'::'L3.2_Ground Subsystems'::'L3.2.1_Behaviors'::'L3.2.1.1_Ground Subsystems Behaviors'::'Ground Subsystems Behavior A' {
                                        doc /* Source XMI: _19_0_2_3880181_1637005128774_844972_55992
                                        Stereotype Refine
                                        UML kind: uml:Abstraction */
                                    }
                                }
                            }
                        }
                        package 'L3.2.2_Structures' {
                            doc /* Source XMI: _18_0_6_3e4019a_1472151563830_693876_14082
                            Comment _19_0_2_3880181_1600958723542_323566_62759
                            The package of Ground subsystems structures:
                            Plan and Schedule
                            Spacecraft Command
                            Ground Equipment Control
                            Space - Ground Communication
                            Mission Data Processing
                            Mission Data Dissemination
                            Network
                            Comment _19_0_3_2b0010b_1619901958651_110787_1202 (HowTo)
                            Select Ground Subsystems Structures Table / Select in Containment Tree to locate Subsystems pkg in the Containment tree
                            Open the Ground Subsystems Structures Table and select Add New to add a new subsystem to the containment tree and to the table.
                            Drag the new subsystem element from the containment tree to the Ground Subsystems bdd
                            Drag the new subsystem element from the containment tree to the Ground Segment bdd.
                            Right click the Ground Segment block and select directed composition and drag to the new subsystem element.
                            Open the Ground Segment Structures Table and right click on Refresh to make the new subsystem a Ground Segment part.
                            Comment _19_0_2_3880181_1637334736623_916214_56102 (Explanation)
                            Ground Subsystems - Popuation
                            UML kind: uml:Package */
                            part def 'Spacecraft Command Subsystem' {
                                doc /* Source XMI: _18_0_6_3e4019a_1472151609442_597347_15823
                                Stereotype Subsystem
                                UML kind: uml:Class */
                                part 'hardware' : OfficialCSRM::'Data'::'01 - CubeSat System Reference Model'::'5 - Architecture'::'L4_Components'::'L4.2_Ground Subsystems Components'::'L4.2.2_Spacecraft Command Components'::'L4.2.2.2_Structures'::'Hardware' {
                                    doc /* Source XMI: _19_0_2_3880181_1561293431375_160659_61498
                                    Stereotype PartProperty
                                    UML aggregation: composite
                                    UML association: _19_0_2_3880181_1561293431375_66290_61497 */
                                }
                                part 'software' : OfficialCSRM::'Data'::'01 - CubeSat System Reference Model'::'5 - Architecture'::'L4_Components'::'L4.2_Ground Subsystems Components'::'L4.2.2_Spacecraft Command Components'::'L4.2.2.2_Structures'::'Software' {
                                    doc /* Source XMI: _19_0_2_3880181_1561293443874_605502_61515
                                    Stereotype PartProperty
                                    UML aggregation: composite
                                    UML association: _19_0_2_3880181_1561293443874_39235_61514 */
                                }
                                part 'procedures' : OfficialCSRM::'Data'::'01 - CubeSat System Reference Model'::'5 - Architecture'::'L4_Components'::'L4.2_Ground Subsystems Components'::'L4.2.2_Spacecraft Command Components'::'L4.2.2.2_Structures'::'Procedures' {
                                    doc /* Source XMI: _19_0_2_3880181_1561293455959_433415_61532
                                    Stereotype PartProperty
                                    UML aggregation: composite
                                    UML association: _19_0_2_3880181_1561293455958_286881_61531 */
                                }
                            }
                            part def 'Mission Data Dissemination Subsystem' {
                                doc /* Source XMI: _18_0_6_3e4019a_1472151609443_348896_15824
                                Stereotype Subsystem
                                UML kind: uml:Class */
                                part 'hardware' : OfficialCSRM::'Data'::'01 - CubeSat System Reference Model'::'5 - Architecture'::'L4_Components'::'L4.2_Ground Subsystems Components'::'L4.2.6_Mission Data Dissemination Components'::'L4.2.6.2_Structures'::'Hardware' {
                                    doc /* Source XMI: _19_0_2_3880181_1561296512193_712760_62334
                                    Stereotype PartProperty
                                    UML aggregation: composite
                                    UML association: _19_0_2_3880181_1561296512193_514114_62333 */
                                }
                                part 'software' : OfficialCSRM::'Data'::'01 - CubeSat System Reference Model'::'5 - Architecture'::'L4_Components'::'L4.2_Ground Subsystems Components'::'L4.2.6_Mission Data Dissemination Components'::'L4.2.6.2_Structures'::'Software' {
                                    doc /* Source XMI: _19_0_2_3880181_1561296524149_445152_62351
                                    Stereotype PartProperty
                                    UML aggregation: composite
                                    UML association: _19_0_2_3880181_1561296524149_135168_62350 */
                                }
                                part 'procedures' : OfficialCSRM::'Data'::'01 - CubeSat System Reference Model'::'5 - Architecture'::'L4_Components'::'L4.2_Ground Subsystems Components'::'L4.2.6_Mission Data Dissemination Components'::'L4.2.6.2_Structures'::'Procedures' {
                                    doc /* Source XMI: _19_0_2_3880181_1561296538675_354509_62368
                                    Stereotype PartProperty
                                    UML aggregation: composite
                                    UML association: _19_0_2_3880181_1561296538675_158786_62367 */
                                }
                            }
                            part def 'Network Subsystem' {
                                doc /* Source XMI: _18_0_6_3e4019a_1472151609444_827746_15825
                                Stereotype Subsystem
                                UML kind: uml:Class */
                                part 'hardware' : OfficialCSRM::'Data'::'01 - CubeSat System Reference Model'::'5 - Architecture'::'L4_Components'::'L4.2_Ground Subsystems Components'::'L4.2.7_Network Components'::'L4.2.7.2_Structures'::'Hardware' {
                                    doc /* Source XMI: _19_0_2_3880181_1561297189672_249905_62551
                                    Stereotype PartProperty
                                    UML aggregation: composite
                                    UML association: _19_0_2_3880181_1561297189672_41171_62550 */
                                }
                                part 'software' : OfficialCSRM::'Data'::'01 - CubeSat System Reference Model'::'5 - Architecture'::'L4_Components'::'L4.2_Ground Subsystems Components'::'L4.2.7_Network Components'::'L4.2.7.2_Structures'::'Software' {
                                    doc /* Source XMI: _19_0_2_3880181_1561297194175_555876_62568
                                    Stereotype PartProperty
                                    UML aggregation: composite
                                    UML association: _19_0_2_3880181_1561297194174_236329_62567 */
                                }
                                part 'procedures' : OfficialCSRM::'Data'::'01 - CubeSat System Reference Model'::'5 - Architecture'::'L4_Components'::'L4.2_Ground Subsystems Components'::'L4.2.7_Network Components'::'L4.2.7.2_Structures'::'Procedures' {
                                    doc /* Source XMI: _19_0_2_3880181_1561297200463_4555_62585
                                    Stereotype PartProperty
                                    UML aggregation: composite
                                    UML association: _19_0_2_3880181_1561297200462_920593_62584 */
                                }
                            }
                            part def 'Space - Ground Communication Subsystem' {
                                doc /* Source XMI: _18_0_6_3e4019a_1472151609445_482519_15826
                                Stereotype Subsystem
                                UML kind: uml:Class */
                                part 'hardware' : OfficialCSRM::'Data'::'01 - CubeSat System Reference Model'::'5 - Architecture'::'L4_Components'::'L4.2_Ground Subsystems Components'::'L4.2.4_Space-Ground Communication Components'::'L4.2.4.2_Structures'::'Hardware' {
                                    doc /* Source XMI: _19_0_2_3880181_1561295566203_739735_61916
                                    Stereotype PartProperty
                                    UML aggregation: composite
                                    UML association: _19_0_2_3880181_1561295566203_274797_61915 */
                                }
                                part 'software' : OfficialCSRM::'Data'::'01 - CubeSat System Reference Model'::'5 - Architecture'::'L4_Components'::'L4.2_Ground Subsystems Components'::'L4.2.4_Space-Ground Communication Components'::'L4.2.4.2_Structures'::'Software' {
                                    doc /* Source XMI: _19_0_2_3880181_1561295582298_648467_61933
                                    Stereotype PartProperty
                                    UML aggregation: composite
                                    UML association: _19_0_2_3880181_1561295582298_771193_61932 */
                                }
                                part 'procedures' : OfficialCSRM::'Data'::'01 - CubeSat System Reference Model'::'5 - Architecture'::'L4_Components'::'L4.2_Ground Subsystems Components'::'L4.2.4_Space-Ground Communication Components'::'L4.2.4.2_Structures'::'Procedures' {
                                    doc /* Source XMI: _19_0_2_3880181_1561295590947_925097_61950
                                    Stereotype PartProperty
                                    UML aggregation: composite
                                    UML association: _19_0_2_3880181_1561295590947_683909_61949 */
                                }
                            }
                            part def 'Mission Data Processing Subsystem' {
                                doc /* Source XMI: _18_0_6_3e4019a_1472151609448_32689_15828
                                Stereotype Subsystem
                                UML kind: uml:Class */
                                part 'harware' : OfficialCSRM::'Data'::'01 - CubeSat System Reference Model'::'5 - Architecture'::'L4_Components'::'L4.2_Ground Subsystems Components'::'L4.2.5_Mission Data Processing Components'::'L4.2.5.2_Structures'::'Hardware' {
                                    doc /* Source XMI: _19_0_2_3880181_1561295991615_753069_62125
                                    Stereotype PartProperty
                                    UML aggregation: composite
                                    UML association: _19_0_2_3880181_1561295991615_827007_62124 */
                                }
                                part 'software' : OfficialCSRM::'Data'::'01 - CubeSat System Reference Model'::'5 - Architecture'::'L4_Components'::'L4.2_Ground Subsystems Components'::'L4.2.5_Mission Data Processing Components'::'L4.2.5.2_Structures'::'Software' {
                                    doc /* Source XMI: _19_0_2_3880181_1561296000323_403758_62142
                                    Stereotype PartProperty
                                    UML aggregation: composite
                                    UML association: _19_0_2_3880181_1561296000322_655342_62141 */
                                }
                                part 'procedures' : OfficialCSRM::'Data'::'01 - CubeSat System Reference Model'::'5 - Architecture'::'L4_Components'::'L4.2_Ground Subsystems Components'::'L4.2.5_Mission Data Processing Components'::'L4.2.5.2_Structures'::'Procedures' {
                                    doc /* Source XMI: _19_0_2_3880181_1561296007441_153519_62159
                                    Stereotype PartProperty
                                    UML aggregation: composite
                                    UML association: _19_0_2_3880181_1561296007441_258165_62158 */
                                }
                            }
                            part def 'Plan and Schedule Subsystem' {
                                doc /* Source XMI: _18_0_6_3e4019a_1472151609449_411899_15829
                                Stereotype Subsystem
                                UML kind: uml:Class */
                                part 'hardware' : OfficialCSRM::'Data'::'01 - CubeSat System Reference Model'::'5 - Architecture'::'L4_Components'::'L4.2_Ground Subsystems Components'::'L4.2.1_Plan and Schedule Components'::'L4.2.1.2_Structures'::'Hardware' {
                                    doc /* Source XMI: _19_0_2_3880181_1561289939669_337880_61202
                                    Stereotype PartProperty
                                    UML aggregation: composite
                                    UML association: _19_0_2_3880181_1561289939669_493611_61201 */
                                }
                                part 'procedures' : OfficialCSRM::'Data'::'01 - CubeSat System Reference Model'::'5 - Architecture'::'L4_Components'::'L4.2_Ground Subsystems Components'::'L4.2.1_Plan and Schedule Components'::'L4.2.1.2_Structures'::'Procedures' {
                                    doc /* Source XMI: _19_0_2_3880181_1561290475692_665848_61259
                                    Stereotype PartProperty
                                    UML aggregation: composite
                                    UML association: _19_0_2_3880181_1561290475692_914718_61258 */
                                }
                                part 'software' : OfficialCSRM::'Data'::'01 - CubeSat System Reference Model'::'5 - Architecture'::'L4_Components'::'L4.2_Ground Subsystems Components'::'L4.2.1_Plan and Schedule Components'::'L4.2.1.2_Structures'::'Software' {
                                    doc /* Source XMI: _19_0_2_3880181_1561290969252_407635_61318
                                    Stereotype PartProperty
                                    UML aggregation: composite
                                    UML association: _19_0_2_3880181_1561290969252_216890_61317 */
                                }
                            }
                            part def 'Ground Equipment Control Subsystem' {
                                doc /* Source XMI: _18_0_6_3e4019a_1472151609449_506433_15830
                                Stereotype Subsystem
                                UML kind: uml:Class */
                                part 'hardware' : OfficialCSRM::'Data'::'01 - CubeSat System Reference Model'::'5 - Architecture'::'L4_Components'::'L4.2_Ground Subsystems Components'::'L4.2.3_Ground Equipment Control Components'::'L4.2.3.2_Structures'::'Hardware' {
                                    doc /* Source XMI: _19_0_2_3880181_1561294399372_972084_61707
                                    Stereotype PartProperty
                                    UML aggregation: composite
                                    UML association: _19_0_2_3880181_1561294399371_232485_61706 */
                                }
                                part 'software' : OfficialCSRM::'Data'::'01 - CubeSat System Reference Model'::'5 - Architecture'::'L4_Components'::'L4.2_Ground Subsystems Components'::'L4.2.3_Ground Equipment Control Components'::'L4.2.3.2_Structures'::'Software' {
                                    doc /* Source XMI: _19_0_2_3880181_1561294406758_865478_61724
                                    Stereotype PartProperty
                                    UML aggregation: composite
                                    UML association: _19_0_2_3880181_1561294406758_281321_61723 */
                                }
                                part 'procedures' : OfficialCSRM::'Data'::'01 - CubeSat System Reference Model'::'5 - Architecture'::'L4_Components'::'L4.2_Ground Subsystems Components'::'L4.2.3_Ground Equipment Control Components'::'L4.2.3.2_Structures'::'Procedures' {
                                    doc /* Source XMI: _19_0_2_3880181_1561294419250_317394_61741
                                    Stereotype PartProperty
                                    UML aggregation: composite
                                    UML association: _19_0_2_3880181_1561294419250_279824_61740 */
                                }
                            }
                            connection def association_10 {
                                doc /* Source XMI: _19_0_2_3880181_1561289939669_493611_61201
                                UML end details are in the source map (SysML v2 connector ends have fixed [1..1] multiplicity). */
                                end end1 : OfficialCSRM::'Data'::'01 - CubeSat System Reference Model'::'5 - Architecture'::'L4_Components'::'L4.2_Ground Subsystems Components'::'L4.2.1_Plan and Schedule Components'::'L4.2.1.2_Structures'::'Hardware' {
                                    doc /* Source XMI: _19_0_2_3880181_1561289939669_337880_61202
                                    Stereotype PartProperty
                                    UML end name: hardware */
                                }
                                end end2 : OfficialCSRM::'Data'::'01 - CubeSat System Reference Model'::'5 - Architecture'::'L3_Subsystems'::'L3.2_Ground Subsystems'::'L3.2.2_Structures'::'Plan and Schedule Subsystem' {
                                    doc /* Source XMI: _19_0_2_3880181_1561289939670_624749_61203
                                    UML end name: (unnamed) */
                                }
                            }
                            connection def association_11 {
                                doc /* Source XMI: _19_0_2_3880181_1561290475692_914718_61258
                                UML end details are in the source map (SysML v2 connector ends have fixed [1..1] multiplicity). */
                                end end1 : OfficialCSRM::'Data'::'01 - CubeSat System Reference Model'::'5 - Architecture'::'L4_Components'::'L4.2_Ground Subsystems Components'::'L4.2.1_Plan and Schedule Components'::'L4.2.1.2_Structures'::'Procedures' {
                                    doc /* Source XMI: _19_0_2_3880181_1561290475692_665848_61259
                                    Stereotype PartProperty
                                    UML end name: procedures */
                                }
                                end end2 : OfficialCSRM::'Data'::'01 - CubeSat System Reference Model'::'5 - Architecture'::'L3_Subsystems'::'L3.2_Ground Subsystems'::'L3.2.2_Structures'::'Plan and Schedule Subsystem' {
                                    doc /* Source XMI: _19_0_2_3880181_1561290475692_790736_61260
                                    UML end name: (unnamed) */
                                }
                            }
                            connection def association_12 {
                                doc /* Source XMI: _19_0_2_3880181_1561290969252_216890_61317
                                UML end details are in the source map (SysML v2 connector ends have fixed [1..1] multiplicity). */
                                end end1 : OfficialCSRM::'Data'::'01 - CubeSat System Reference Model'::'5 - Architecture'::'L4_Components'::'L4.2_Ground Subsystems Components'::'L4.2.1_Plan and Schedule Components'::'L4.2.1.2_Structures'::'Software' {
                                    doc /* Source XMI: _19_0_2_3880181_1561290969252_407635_61318
                                    Stereotype PartProperty
                                    UML end name: software */
                                }
                                end end2 : OfficialCSRM::'Data'::'01 - CubeSat System Reference Model'::'5 - Architecture'::'L3_Subsystems'::'L3.2_Ground Subsystems'::'L3.2.2_Structures'::'Plan and Schedule Subsystem' {
                                    doc /* Source XMI: _19_0_2_3880181_1561290969253_53641_61319
                                    UML end name: (unnamed) */
                                }
                            }
                            connection def association_13 {
                                doc /* Source XMI: _19_0_2_3880181_1561293431375_66290_61497
                                UML end details are in the source map (SysML v2 connector ends have fixed [1..1] multiplicity). */
                                end end1 : OfficialCSRM::'Data'::'01 - CubeSat System Reference Model'::'5 - Architecture'::'L4_Components'::'L4.2_Ground Subsystems Components'::'L4.2.2_Spacecraft Command Components'::'L4.2.2.2_Structures'::'Hardware' {
                                    doc /* Source XMI: _19_0_2_3880181_1561293431375_160659_61498
                                    Stereotype PartProperty
                                    UML end name: hardware */
                                }
                                end end2 : OfficialCSRM::'Data'::'01 - CubeSat System Reference Model'::'5 - Architecture'::'L3_Subsystems'::'L3.2_Ground Subsystems'::'L3.2.2_Structures'::'Spacecraft Command Subsystem' {
                                    doc /* Source XMI: _19_0_2_3880181_1561293431375_535948_61499
                                    UML end name: (unnamed) */
                                }
                            }
                            connection def association_14 {
                                doc /* Source XMI: _19_0_2_3880181_1561293443874_39235_61514
                                UML end details are in the source map (SysML v2 connector ends have fixed [1..1] multiplicity). */
                                end end1 : OfficialCSRM::'Data'::'01 - CubeSat System Reference Model'::'5 - Architecture'::'L4_Components'::'L4.2_Ground Subsystems Components'::'L4.2.2_Spacecraft Command Components'::'L4.2.2.2_Structures'::'Software' {
                                    doc /* Source XMI: _19_0_2_3880181_1561293443874_605502_61515
                                    Stereotype PartProperty
                                    UML end name: software */
                                }
                                end end2 : OfficialCSRM::'Data'::'01 - CubeSat System Reference Model'::'5 - Architecture'::'L3_Subsystems'::'L3.2_Ground Subsystems'::'L3.2.2_Structures'::'Spacecraft Command Subsystem' {
                                    doc /* Source XMI: _19_0_2_3880181_1561293443874_705220_61516
                                    UML end name: (unnamed) */
                                }
                            }
                            connection def association_15 {
                                doc /* Source XMI: _19_0_2_3880181_1561293455958_286881_61531
                                UML end details are in the source map (SysML v2 connector ends have fixed [1..1] multiplicity). */
                                end end1 : OfficialCSRM::'Data'::'01 - CubeSat System Reference Model'::'5 - Architecture'::'L4_Components'::'L4.2_Ground Subsystems Components'::'L4.2.2_Spacecraft Command Components'::'L4.2.2.2_Structures'::'Procedures' {
                                    doc /* Source XMI: _19_0_2_3880181_1561293455959_433415_61532
                                    Stereotype PartProperty
                                    UML end name: procedures */
                                }
                                end end2 : OfficialCSRM::'Data'::'01 - CubeSat System Reference Model'::'5 - Architecture'::'L3_Subsystems'::'L3.2_Ground Subsystems'::'L3.2.2_Structures'::'Spacecraft Command Subsystem' {
                                    doc /* Source XMI: _19_0_2_3880181_1561293455959_859447_61533
                                    UML end name: (unnamed) */
                                }
                            }
                            connection def association_16 {
                                doc /* Source XMI: _19_0_2_3880181_1561294399371_232485_61706
                                UML end details are in the source map (SysML v2 connector ends have fixed [1..1] multiplicity). */
                                end end1 : OfficialCSRM::'Data'::'01 - CubeSat System Reference Model'::'5 - Architecture'::'L4_Components'::'L4.2_Ground Subsystems Components'::'L4.2.3_Ground Equipment Control Components'::'L4.2.3.2_Structures'::'Hardware' {
                                    doc /* Source XMI: _19_0_2_3880181_1561294399372_972084_61707
                                    Stereotype PartProperty
                                    UML end name: hardware */
                                }
                                end end2 : OfficialCSRM::'Data'::'01 - CubeSat System Reference Model'::'5 - Architecture'::'L3_Subsystems'::'L3.2_Ground Subsystems'::'L3.2.2_Structures'::'Ground Equipment Control Subsystem' {
                                    doc /* Source XMI: _19_0_2_3880181_1561294399372_225784_61708
                                    UML end name: (unnamed) */
                                }
                            }
                            connection def association_17 {
                                doc /* Source XMI: _19_0_2_3880181_1561294406758_281321_61723
                                UML end details are in the source map (SysML v2 connector ends have fixed [1..1] multiplicity). */
                                end end1 : OfficialCSRM::'Data'::'01 - CubeSat System Reference Model'::'5 - Architecture'::'L4_Components'::'L4.2_Ground Subsystems Components'::'L4.2.3_Ground Equipment Control Components'::'L4.2.3.2_Structures'::'Software' {
                                    doc /* Source XMI: _19_0_2_3880181_1561294406758_865478_61724
                                    Stereotype PartProperty
                                    UML end name: software */
                                }
                                end end2 : OfficialCSRM::'Data'::'01 - CubeSat System Reference Model'::'5 - Architecture'::'L3_Subsystems'::'L3.2_Ground Subsystems'::'L3.2.2_Structures'::'Ground Equipment Control Subsystem' {
                                    doc /* Source XMI: _19_0_2_3880181_1561294406758_663605_61725
                                    UML end name: (unnamed) */
                                }
                            }
                            connection def association_18 {
                                doc /* Source XMI: _19_0_2_3880181_1561294419250_279824_61740
                                UML end details are in the source map (SysML v2 connector ends have fixed [1..1] multiplicity). */
                                end end1 : OfficialCSRM::'Data'::'01 - CubeSat System Reference Model'::'5 - Architecture'::'L4_Components'::'L4.2_Ground Subsystems Components'::'L4.2.3_Ground Equipment Control Components'::'L4.2.3.2_Structures'::'Procedures' {
                                    doc /* Source XMI: _19_0_2_3880181_1561294419250_317394_61741
                                    Stereotype PartProperty
                                    UML end name: procedures */
                                }
                                end end2 : OfficialCSRM::'Data'::'01 - CubeSat System Reference Model'::'5 - Architecture'::'L3_Subsystems'::'L3.2_Ground Subsystems'::'L3.2.2_Structures'::'Ground Equipment Control Subsystem' {
                                    doc /* Source XMI: _19_0_2_3880181_1561294419251_342265_61742
                                    UML end name: (unnamed) */
                                }
                            }
                            connection def association_19 {
                                doc /* Source XMI: _19_0_2_3880181_1561295566203_274797_61915
                                UML end details are in the source map (SysML v2 connector ends have fixed [1..1] multiplicity). */
                                end end1 : OfficialCSRM::'Data'::'01 - CubeSat System Reference Model'::'5 - Architecture'::'L4_Components'::'L4.2_Ground Subsystems Components'::'L4.2.4_Space-Ground Communication Components'::'L4.2.4.2_Structures'::'Hardware' {
                                    doc /* Source XMI: _19_0_2_3880181_1561295566203_739735_61916
                                    Stereotype PartProperty
                                    UML end name: hardware */
                                }
                                end end2 : OfficialCSRM::'Data'::'01 - CubeSat System Reference Model'::'5 - Architecture'::'L3_Subsystems'::'L3.2_Ground Subsystems'::'L3.2.2_Structures'::'Space - Ground Communication Subsystem' {
                                    doc /* Source XMI: _19_0_2_3880181_1561295566203_605271_61917
                                    UML end name: (unnamed) */
                                }
                            }
                            connection def association_20 {
                                doc /* Source XMI: _19_0_2_3880181_1561295582298_771193_61932
                                UML end details are in the source map (SysML v2 connector ends have fixed [1..1] multiplicity). */
                                end end1 : OfficialCSRM::'Data'::'01 - CubeSat System Reference Model'::'5 - Architecture'::'L4_Components'::'L4.2_Ground Subsystems Components'::'L4.2.4_Space-Ground Communication Components'::'L4.2.4.2_Structures'::'Software' {
                                    doc /* Source XMI: _19_0_2_3880181_1561295582298_648467_61933
                                    Stereotype PartProperty
                                    UML end name: software */
                                }
                                end end2 : OfficialCSRM::'Data'::'01 - CubeSat System Reference Model'::'5 - Architecture'::'L3_Subsystems'::'L3.2_Ground Subsystems'::'L3.2.2_Structures'::'Space - Ground Communication Subsystem' {
                                    doc /* Source XMI: _19_0_2_3880181_1561295582299_751497_61934
                                    UML end name: (unnamed) */
                                }
                            }
                            connection def association_21 {
                                doc /* Source XMI: _19_0_2_3880181_1561295590947_683909_61949
                                UML end details are in the source map (SysML v2 connector ends have fixed [1..1] multiplicity). */
                                end end1 : OfficialCSRM::'Data'::'01 - CubeSat System Reference Model'::'5 - Architecture'::'L4_Components'::'L4.2_Ground Subsystems Components'::'L4.2.4_Space-Ground Communication Components'::'L4.2.4.2_Structures'::'Procedures' {
                                    doc /* Source XMI: _19_0_2_3880181_1561295590947_925097_61950
                                    Stereotype PartProperty
                                    UML end name: procedures */
                                }
                                end end2 : OfficialCSRM::'Data'::'01 - CubeSat System Reference Model'::'5 - Architecture'::'L3_Subsystems'::'L3.2_Ground Subsystems'::'L3.2.2_Structures'::'Space - Ground Communication Subsystem' {
                                    doc /* Source XMI: _19_0_2_3880181_1561295590948_209318_61951
                                    UML end name: (unnamed) */
                                }
                            }
                            connection def association_22 {
                                doc /* Source XMI: _19_0_2_3880181_1561295991615_827007_62124
                                UML end details are in the source map (SysML v2 connector ends have fixed [1..1] multiplicity). */
                                end end1 : OfficialCSRM::'Data'::'01 - CubeSat System Reference Model'::'5 - Architecture'::'L4_Components'::'L4.2_Ground Subsystems Components'::'L4.2.5_Mission Data Processing Components'::'L4.2.5.2_Structures'::'Hardware' {
                                    doc /* Source XMI: _19_0_2_3880181_1561295991615_753069_62125
                                    Stereotype PartProperty
                                    UML end name: harware */
                                }
                                end end2 : OfficialCSRM::'Data'::'01 - CubeSat System Reference Model'::'5 - Architecture'::'L3_Subsystems'::'L3.2_Ground Subsystems'::'L3.2.2_Structures'::'Mission Data Processing Subsystem' {
                                    doc /* Source XMI: _19_0_2_3880181_1561295991615_679854_62126
                                    UML end name: (unnamed) */
                                }
                            }
                            connection def association_23 {
                                doc /* Source XMI: _19_0_2_3880181_1561296000322_655342_62141
                                UML end details are in the source map (SysML v2 connector ends have fixed [1..1] multiplicity). */
                                end end1 : OfficialCSRM::'Data'::'01 - CubeSat System Reference Model'::'5 - Architecture'::'L4_Components'::'L4.2_Ground Subsystems Components'::'L4.2.5_Mission Data Processing Components'::'L4.2.5.2_Structures'::'Software' {
                                    doc /* Source XMI: _19_0_2_3880181_1561296000323_403758_62142
                                    Stereotype PartProperty
                                    UML end name: software */
                                }
                                end end2 : OfficialCSRM::'Data'::'01 - CubeSat System Reference Model'::'5 - Architecture'::'L3_Subsystems'::'L3.2_Ground Subsystems'::'L3.2.2_Structures'::'Mission Data Processing Subsystem' {
                                    doc /* Source XMI: _19_0_2_3880181_1561296000323_111099_62143
                                    UML end name: (unnamed) */
                                }
                            }
                            connection def association_24 {
                                doc /* Source XMI: _19_0_2_3880181_1561296007441_258165_62158
                                UML end details are in the source map (SysML v2 connector ends have fixed [1..1] multiplicity). */
                                end end1 : OfficialCSRM::'Data'::'01 - CubeSat System Reference Model'::'5 - Architecture'::'L4_Components'::'L4.2_Ground Subsystems Components'::'L4.2.5_Mission Data Processing Components'::'L4.2.5.2_Structures'::'Procedures' {
                                    doc /* Source XMI: _19_0_2_3880181_1561296007441_153519_62159
                                    Stereotype PartProperty
                                    UML end name: procedures */
                                }
                                end end2 : OfficialCSRM::'Data'::'01 - CubeSat System Reference Model'::'5 - Architecture'::'L3_Subsystems'::'L3.2_Ground Subsystems'::'L3.2.2_Structures'::'Mission Data Processing Subsystem' {
                                    doc /* Source XMI: _19_0_2_3880181_1561296007442_840687_62160
                                    UML end name: (unnamed) */
                                }
                            }
                            connection def association_25 {
                                doc /* Source XMI: _19_0_2_3880181_1561296512193_514114_62333
                                UML end details are in the source map (SysML v2 connector ends have fixed [1..1] multiplicity). */
                                end end1 : OfficialCSRM::'Data'::'01 - CubeSat System Reference Model'::'5 - Architecture'::'L4_Components'::'L4.2_Ground Subsystems Components'::'L4.2.6_Mission Data Dissemination Components'::'L4.2.6.2_Structures'::'Hardware' {
                                    doc /* Source XMI: _19_0_2_3880181_1561296512193_712760_62334
                                    Stereotype PartProperty
                                    UML end name: hardware */
                                }
                                end end2 : OfficialCSRM::'Data'::'01 - CubeSat System Reference Model'::'5 - Architecture'::'L3_Subsystems'::'L3.2_Ground Subsystems'::'L3.2.2_Structures'::'Mission Data Dissemination Subsystem' {
                                    doc /* Source XMI: _19_0_2_3880181_1561296512193_318940_62335
                                    UML end name: (unnamed) */
                                }
                            }
                            connection def association_26 {
                                doc /* Source XMI: _19_0_2_3880181_1561296524149_135168_62350
                                UML end details are in the source map (SysML v2 connector ends have fixed [1..1] multiplicity). */
                                end end1 : OfficialCSRM::'Data'::'01 - CubeSat System Reference Model'::'5 - Architecture'::'L4_Components'::'L4.2_Ground Subsystems Components'::'L4.2.6_Mission Data Dissemination Components'::'L4.2.6.2_Structures'::'Software' {
                                    doc /* Source XMI: _19_0_2_3880181_1561296524149_445152_62351
                                    Stereotype PartProperty
                                    UML end name: software */
                                }
                                end end2 : OfficialCSRM::'Data'::'01 - CubeSat System Reference Model'::'5 - Architecture'::'L3_Subsystems'::'L3.2_Ground Subsystems'::'L3.2.2_Structures'::'Mission Data Dissemination Subsystem' {
                                    doc /* Source XMI: _19_0_2_3880181_1561296524150_864578_62352
                                    UML end name: (unnamed) */
                                }
                            }
                            connection def association_27 {
                                doc /* Source XMI: _19_0_2_3880181_1561296538675_158786_62367
                                UML end details are in the source map (SysML v2 connector ends have fixed [1..1] multiplicity). */
                                end end1 : OfficialCSRM::'Data'::'01 - CubeSat System Reference Model'::'5 - Architecture'::'L4_Components'::'L4.2_Ground Subsystems Components'::'L4.2.6_Mission Data Dissemination Components'::'L4.2.6.2_Structures'::'Procedures' {
                                    doc /* Source XMI: _19_0_2_3880181_1561296538675_354509_62368
                                    Stereotype PartProperty
                                    UML end name: procedures */
                                }
                                end end2 : OfficialCSRM::'Data'::'01 - CubeSat System Reference Model'::'5 - Architecture'::'L3_Subsystems'::'L3.2_Ground Subsystems'::'L3.2.2_Structures'::'Mission Data Dissemination Subsystem' {
                                    doc /* Source XMI: _19_0_2_3880181_1561296538676_480493_62369
                                    UML end name: (unnamed) */
                                }
                            }
                            connection def association_28 {
                                doc /* Source XMI: _19_0_2_3880181_1561297189672_41171_62550
                                UML end details are in the source map (SysML v2 connector ends have fixed [1..1] multiplicity). */
                                end end1 : OfficialCSRM::'Data'::'01 - CubeSat System Reference Model'::'5 - Architecture'::'L4_Components'::'L4.2_Ground Subsystems Components'::'L4.2.7_Network Components'::'L4.2.7.2_Structures'::'Hardware' {
                                    doc /* Source XMI: _19_0_2_3880181_1561297189672_249905_62551
                                    Stereotype PartProperty
                                    UML end name: hardware */
                                }
                                end end2 : OfficialCSRM::'Data'::'01 - CubeSat System Reference Model'::'5 - Architecture'::'L3_Subsystems'::'L3.2_Ground Subsystems'::'L3.2.2_Structures'::'Network Subsystem' {
                                    doc /* Source XMI: _19_0_2_3880181_1561297189672_935040_62552
                                    UML end name: (unnamed) */
                                }
                            }
                            connection def association_29 {
                                doc /* Source XMI: _19_0_2_3880181_1561297194174_236329_62567
                                UML end details are in the source map (SysML v2 connector ends have fixed [1..1] multiplicity). */
                                end end1 : OfficialCSRM::'Data'::'01 - CubeSat System Reference Model'::'5 - Architecture'::'L4_Components'::'L4.2_Ground Subsystems Components'::'L4.2.7_Network Components'::'L4.2.7.2_Structures'::'Software' {
                                    doc /* Source XMI: _19_0_2_3880181_1561297194175_555876_62568
                                    Stereotype PartProperty
                                    UML end name: software */
                                }
                                end end2 : OfficialCSRM::'Data'::'01 - CubeSat System Reference Model'::'5 - Architecture'::'L3_Subsystems'::'L3.2_Ground Subsystems'::'L3.2.2_Structures'::'Network Subsystem' {
                                    doc /* Source XMI: _19_0_2_3880181_1561297194175_489069_62569
                                    UML end name: (unnamed) */
                                }
                            }
                            connection def association_30 {
                                doc /* Source XMI: _19_0_2_3880181_1561297200462_920593_62584
                                UML end details are in the source map (SysML v2 connector ends have fixed [1..1] multiplicity). */
                                end end1 : OfficialCSRM::'Data'::'01 - CubeSat System Reference Model'::'5 - Architecture'::'L4_Components'::'L4.2_Ground Subsystems Components'::'L4.2.7_Network Components'::'L4.2.7.2_Structures'::'Procedures' {
                                    doc /* Source XMI: _19_0_2_3880181_1561297200463_4555_62585
                                    Stereotype PartProperty
                                    UML end name: procedures */
                                }
                                end end2 : OfficialCSRM::'Data'::'01 - CubeSat System Reference Model'::'5 - Architecture'::'L3_Subsystems'::'L3.2_Ground Subsystems'::'L3.2.2_Structures'::'Network Subsystem' {
                                    doc /* Source XMI: _19_0_2_3880181_1561297200463_165151_62586
                                    UML end name: (unnamed) */
                                }
                            }
                            part def 'Facilities Subsystem' {
                                doc /* Source XMI: _19_0_2_3880181_1652559609874_213754_58531
                                Stereotype Subsystem
                                UML kind: uml:Class */
                                part 'room' : OfficialCSRM::'Data'::'01 - CubeSat System Reference Model'::'5 - Architecture'::'L4_Components'::'L4.2_Ground Subsystems Components'::'L4.2.8_Facility Components'::'L4.2.8.2_Structures'::'Room' {
                                    doc /* Source XMI: _19_0_2_3880181_1652710899748_143647_59315
                                    Stereotype PartProperty
                                    UML aggregation: composite
                                    UML association: _19_0_2_3880181_1652710899748_489705_59314 */
                                }
                                part 'room 2' : OfficialCSRM::'Data'::'01 - CubeSat System Reference Model'::'5 - Architecture'::'L4_Components'::'L4.2_Ground Subsystems Components'::'L4.2.8_Facility Components'::'L4.2.8.2_Structures'::'Room 2' {
                                    doc /* Source XMI: _19_0_2_3880181_1652714498627_437226_59000
                                    Stereotype PartProperty
                                    UML aggregation: composite
                                    UML association: _19_0_2_3880181_1652714498627_851997_58999 */
                                }
                            }
                            connection def association_32 {
                                doc /* Source XMI: _19_0_2_3880181_1652710899748_489705_59314
                                UML end details are in the source map (SysML v2 connector ends have fixed [1..1] multiplicity). */
                                end end1 : OfficialCSRM::'Data'::'01 - CubeSat System Reference Model'::'5 - Architecture'::'L4_Components'::'L4.2_Ground Subsystems Components'::'L4.2.8_Facility Components'::'L4.2.8.2_Structures'::'Room' {
                                    doc /* Source XMI: _19_0_2_3880181_1652710899748_143647_59315
                                    Stereotype PartProperty
                                    UML end name: room */
                                }
                                end end2 : OfficialCSRM::'Data'::'01 - CubeSat System Reference Model'::'5 - Architecture'::'L3_Subsystems'::'L3.2_Ground Subsystems'::'L3.2.2_Structures'::'Facilities Subsystem' {
                                    doc /* Source XMI: _19_0_2_3880181_1652710899748_321662_59316
                                    UML end name: (unnamed) */
                                }
                            }
                            connection def association_33 {
                                doc /* Source XMI: _19_0_2_3880181_1652714498627_851997_58999
                                UML end details are in the source map (SysML v2 connector ends have fixed [1..1] multiplicity). */
                                end end1 : OfficialCSRM::'Data'::'01 - CubeSat System Reference Model'::'5 - Architecture'::'L4_Components'::'L4.2_Ground Subsystems Components'::'L4.2.8_Facility Components'::'L4.2.8.2_Structures'::'Room 2' {
                                    doc /* Source XMI: _19_0_2_3880181_1652714498627_437226_59000
                                    Stereotype PartProperty
                                    UML end name: room 2 */
                                }
                                end end2 : OfficialCSRM::'Data'::'01 - CubeSat System Reference Model'::'5 - Architecture'::'L3_Subsystems'::'L3.2_Ground Subsystems'::'L3.2.2_Structures'::'Facilities Subsystem' {
                                    doc /* Source XMI: _19_0_2_3880181_1652714498627_347022_59001
                                    UML end name: (unnamed) */
                                }
                            }
                        }
                    }
                }
                package 'L2_Segment' {
                    doc /* Source XMI: _18_0_6_3e4019a_1472151507106_775245_12341
                    Comment _19_0_2_3880181_1600787152003_668178_62949
                    Package of Space Segment and Ground Segment packages.
                    UML kind: uml:Package */
                    package 'L2.2_Ground Segment' {
                        doc /* Source XMI: _18_0_6_3e4019a_1472151552164_573372_13479
                        Comment _19_0_2_3880181_1600891537262_890234_62864
                        Package of Ground segment behaviors and structures
                        The Ground Segment consists of the CubeSat Mission Operations and one or more Ground Stations.
                        Mission Operations includes the software, data, procedures, and personnel used to operate the CubeSat mission. Mission Operations activities include mission planning and scheduling, command and control of the CubeSat, control of the ground equipment, mission telemetry processing, and mission data processing and distribution.
                        The Ground Station consists of the computers, network, communication equipment, and associated control infrastructure hosted in ground facilities. Communication equipment includes the space-ground antennas.
                        UML kind: uml:Package */
                        package 'L2.2.2_Structures' {
                            doc /* Source XMI: _18_0_6_3e4019a_1472151563822_903433_14065
                            UML kind: uml:Package */
                            part def 'Ground Segment' {
                                @OfficialCSRMProfile::'Architecture Structures Profile'::'Segment';
                                doc /* Source XMI: _18_0_6_3e4019a_1472151573820_820968_14607
                                Stereotype Segment
                                UML kind: uml:Class */
                                part 'plan and Schedule Subsystem' : OfficialCSRM::'Data'::'01 - CubeSat System Reference Model'::'5 - Architecture'::'L3_Subsystems'::'L3.2_Ground Subsystems'::'L3.2.2_Structures'::'Plan and Schedule Subsystem' {
                                    doc /* Source XMI: _18_5_1_3880181_1504962854689_704599_59045
                                    Stereotype PartProperty
                                    UML aggregation: composite
                                    UML association: _18_5_1_3880181_1504962854689_718645_59044 */
                                }
                                part 'spacecraft Command Subsystem' : OfficialCSRM::'Data'::'01 - CubeSat System Reference Model'::'5 - Architecture'::'L3_Subsystems'::'L3.2_Ground Subsystems'::'L3.2.2_Structures'::'Spacecraft Command Subsystem' {
                                    doc /* Source XMI: _18_5_1_3880181_1504962862926_976743_59076
                                    Stereotype PartProperty
                                    UML aggregation: composite
                                    UML association: _18_5_1_3880181_1504962862926_568701_59075 */
                                }
                                part 'ground Equipment Control Subsystem' : OfficialCSRM::'Data'::'01 - CubeSat System Reference Model'::'5 - Architecture'::'L3_Subsystems'::'L3.2_Ground Subsystems'::'L3.2.2_Structures'::'Ground Equipment Control Subsystem' {
                                    doc /* Source XMI: _18_5_1_3880181_1504962895338_974852_59107
                                    Stereotype PartProperty
                                    UML aggregation: composite
                                    UML association: _18_5_1_3880181_1504962895338_261511_59106 */
                                }
                                part 'space - Ground Communication Subsystem' : OfficialCSRM::'Data'::'01 - CubeSat System Reference Model'::'5 - Architecture'::'L3_Subsystems'::'L3.2_Ground Subsystems'::'L3.2.2_Structures'::'Space - Ground Communication Subsystem' {
                                    doc /* Source XMI: _18_5_1_3880181_1504963053369_130151_59176
                                    Stereotype PartProperty
                                    UML aggregation: composite
                                    UML association: _18_5_1_3880181_1504963053369_612270_59175 */
                                }
                                part 'mission Data Processing Subsystem' : OfficialCSRM::'Data'::'01 - CubeSat System Reference Model'::'5 - Architecture'::'L3_Subsystems'::'L3.2_Ground Subsystems'::'L3.2.2_Structures'::'Mission Data Processing Subsystem' {
                                    doc /* Source XMI: _18_5_1_3880181_1504963078577_516768_59259
                                    Stereotype PartProperty
                                    UML aggregation: composite
                                    UML association: _18_5_1_3880181_1504963078577_351696_59258 */
                                }
                                part 'network Subsystem' : OfficialCSRM::'Data'::'01 - CubeSat System Reference Model'::'5 - Architecture'::'L3_Subsystems'::'L3.2_Ground Subsystems'::'L3.2.2_Structures'::'Network Subsystem' {
                                    doc /* Source XMI: _18_5_1_3880181_1504963084625_224047_59290
                                    Stereotype PartProperty
                                    UML aggregation: composite
                                    UML association: _18_5_1_3880181_1504963084625_936319_59289 */
                                }
                                part 'mission Data Dissemination Subsystem' : OfficialCSRM::'Data'::'01 - CubeSat System Reference Model'::'5 - Architecture'::'L3_Subsystems'::'L3.2_Ground Subsystems'::'L3.2.2_Structures'::'Mission Data Dissemination Subsystem' {
                                    doc /* Source XMI: _18_5_1_3880181_1504963090313_225604_59321
                                    Stereotype PartProperty
                                    UML aggregation: composite
                                    UML association: _18_5_1_3880181_1504963090313_415130_59320 */
                                }
                                part 'facilities Subsystem' : OfficialCSRM::'Data'::'01 - CubeSat System Reference Model'::'5 - Architecture'::'L3_Subsystems'::'L3.2_Ground Subsystems'::'L3.2.2_Structures'::'Facilities Subsystem' {
                                    doc /* Source XMI: _19_0_2_3880181_1652560120120_870608_58712
                                    Stereotype PartProperty
                                    UML aggregation: composite
                                    UML association: _19_0_2_3880181_1652560120120_387352_58711 */
                                }
                            }
                            connection def association_1 {
                                doc /* Source XMI: _18_5_1_3880181_1504962854689_718645_59044
                                UML end details are in the source map (SysML v2 connector ends have fixed [1..1] multiplicity). */
                                end end1 : OfficialCSRM::'Data'::'01 - CubeSat System Reference Model'::'5 - Architecture'::'L3_Subsystems'::'L3.2_Ground Subsystems'::'L3.2.2_Structures'::'Plan and Schedule Subsystem' {
                                    doc /* Source XMI: _18_5_1_3880181_1504962854689_704599_59045
                                    Stereotype PartProperty
                                    UML end name: plan and Schedule Subsystem */
                                }
                                end end2 : OfficialCSRM::'Data'::'01 - CubeSat System Reference Model'::'5 - Architecture'::'L2_Segment'::'L2.2_Ground Segment'::'L2.2.2_Structures'::'Ground Segment' {
                                    doc /* Source XMI: _18_5_1_3880181_1504962854689_598274_59046
                                    UML end name: (unnamed) */
                                }
                            }
                            connection def association_2 {
                                doc /* Source XMI: _18_5_1_3880181_1504962862926_568701_59075
                                UML end details are in the source map (SysML v2 connector ends have fixed [1..1] multiplicity). */
                                end end1 : OfficialCSRM::'Data'::'01 - CubeSat System Reference Model'::'5 - Architecture'::'L3_Subsystems'::'L3.2_Ground Subsystems'::'L3.2.2_Structures'::'Spacecraft Command Subsystem' {
                                    doc /* Source XMI: _18_5_1_3880181_1504962862926_976743_59076
                                    Stereotype PartProperty
                                    UML end name: spacecraft Command Subsystem */
                                }
                                end end2 : OfficialCSRM::'Data'::'01 - CubeSat System Reference Model'::'5 - Architecture'::'L2_Segment'::'L2.2_Ground Segment'::'L2.2.2_Structures'::'Ground Segment' {
                                    doc /* Source XMI: _18_5_1_3880181_1504962862926_570827_59077
                                    UML end name: (unnamed) */
                                }
                            }
                            connection def association_3 {
                                doc /* Source XMI: _18_5_1_3880181_1504962895338_261511_59106
                                UML end details are in the source map (SysML v2 connector ends have fixed [1..1] multiplicity). */
                                end end1 : OfficialCSRM::'Data'::'01 - CubeSat System Reference Model'::'5 - Architecture'::'L3_Subsystems'::'L3.2_Ground Subsystems'::'L3.2.2_Structures'::'Ground Equipment Control Subsystem' {
                                    doc /* Source XMI: _18_5_1_3880181_1504962895338_974852_59107
                                    Stereotype PartProperty
                                    UML end name: ground Equipment Control Subsystem */
                                }
                                end end2 : OfficialCSRM::'Data'::'01 - CubeSat System Reference Model'::'5 - Architecture'::'L2_Segment'::'L2.2_Ground Segment'::'L2.2.2_Structures'::'Ground Segment' {
                                    doc /* Source XMI: _18_5_1_3880181_1504962895338_213674_59108
                                    UML end name: (unnamed) */
                                }
                            }
                            connection def association_4 {
                                doc /* Source XMI: _18_5_1_3880181_1504963053369_612270_59175
                                UML end details are in the source map (SysML v2 connector ends have fixed [1..1] multiplicity). */
                                end end1 : OfficialCSRM::'Data'::'01 - CubeSat System Reference Model'::'5 - Architecture'::'L3_Subsystems'::'L3.2_Ground Subsystems'::'L3.2.2_Structures'::'Space - Ground Communication Subsystem' {
                                    doc /* Source XMI: _18_5_1_3880181_1504963053369_130151_59176
                                    Stereotype PartProperty
                                    UML end name: space - Ground Communication Subsystem */
                                }
                                end end2 : OfficialCSRM::'Data'::'01 - CubeSat System Reference Model'::'5 - Architecture'::'L2_Segment'::'L2.2_Ground Segment'::'L2.2.2_Structures'::'Ground Segment' {
                                    doc /* Source XMI: _18_5_1_3880181_1504963053369_207537_59177
                                    UML end name: (unnamed) */
                                }
                            }
                            connection def association_5 {
                                doc /* Source XMI: _18_5_1_3880181_1504963078577_351696_59258
                                UML end details are in the source map (SysML v2 connector ends have fixed [1..1] multiplicity). */
                                end end1 : OfficialCSRM::'Data'::'01 - CubeSat System Reference Model'::'5 - Architecture'::'L3_Subsystems'::'L3.2_Ground Subsystems'::'L3.2.2_Structures'::'Mission Data Processing Subsystem' {
                                    doc /* Source XMI: _18_5_1_3880181_1504963078577_516768_59259
                                    Stereotype PartProperty
                                    UML end name: mission Data Processing Subsystem */
                                }
                                end end2 : OfficialCSRM::'Data'::'01 - CubeSat System Reference Model'::'5 - Architecture'::'L2_Segment'::'L2.2_Ground Segment'::'L2.2.2_Structures'::'Ground Segment' {
                                    doc /* Source XMI: _18_5_1_3880181_1504963078577_825399_59260
                                    UML end name: (unnamed) */
                                }
                            }
                            connection def association_6 {
                                doc /* Source XMI: _18_5_1_3880181_1504963084625_936319_59289
                                UML end details are in the source map (SysML v2 connector ends have fixed [1..1] multiplicity). */
                                end end1 : OfficialCSRM::'Data'::'01 - CubeSat System Reference Model'::'5 - Architecture'::'L3_Subsystems'::'L3.2_Ground Subsystems'::'L3.2.2_Structures'::'Network Subsystem' {
                                    doc /* Source XMI: _18_5_1_3880181_1504963084625_224047_59290
                                    Stereotype PartProperty
                                    UML end name: network Subsystem */
                                }
                                end end2 : OfficialCSRM::'Data'::'01 - CubeSat System Reference Model'::'5 - Architecture'::'L2_Segment'::'L2.2_Ground Segment'::'L2.2.2_Structures'::'Ground Segment' {
                                    doc /* Source XMI: _18_5_1_3880181_1504963084625_441292_59291
                                    UML end name: (unnamed) */
                                }
                            }
                            connection def association_7 {
                                doc /* Source XMI: _18_5_1_3880181_1504963090313_415130_59320
                                UML end details are in the source map (SysML v2 connector ends have fixed [1..1] multiplicity). */
                                end end1 : OfficialCSRM::'Data'::'01 - CubeSat System Reference Model'::'5 - Architecture'::'L3_Subsystems'::'L3.2_Ground Subsystems'::'L3.2.2_Structures'::'Mission Data Dissemination Subsystem' {
                                    doc /* Source XMI: _18_5_1_3880181_1504963090313_225604_59321
                                    Stereotype PartProperty
                                    UML end name: mission Data Dissemination Subsystem */
                                }
                                end end2 : OfficialCSRM::'Data'::'01 - CubeSat System Reference Model'::'5 - Architecture'::'L2_Segment'::'L2.2_Ground Segment'::'L2.2.2_Structures'::'Ground Segment' {
                                    doc /* Source XMI: _18_5_1_3880181_1504963090329_410645_59322
                                    UML end name: (unnamed) */
                                }
                            }
                            connection def association_8 {
                                doc /* Source XMI: _19_0_2_3880181_1652560120120_387352_58711
                                UML end details are in the source map (SysML v2 connector ends have fixed [1..1] multiplicity). */
                                end end1 : OfficialCSRM::'Data'::'01 - CubeSat System Reference Model'::'5 - Architecture'::'L3_Subsystems'::'L3.2_Ground Subsystems'::'L3.2.2_Structures'::'Facilities Subsystem' {
                                    doc /* Source XMI: _19_0_2_3880181_1652560120120_870608_58712
                                    Stereotype PartProperty
                                    UML end name: facilities Subsystem */
                                }
                                end end2 : OfficialCSRM::'Data'::'01 - CubeSat System Reference Model'::'5 - Architecture'::'L2_Segment'::'L2.2_Ground Segment'::'L2.2.2_Structures'::'Ground Segment' {
                                    doc /* Source XMI: _19_0_2_3880181_1652560120120_486065_58713
                                    UML end name: (unnamed) */
                                }
                            }
                        }
                        package 'L2.2.1_Behaviors' {
                            doc /* Source XMI: _18_5_1_3880181_1506467389728_624955_59667
                            Comment _19_0_2_3880181_1601214137018_252065_62969
                            Package of Ground Segment behaviors, use cases, and activities.  For population by a mission-specific team.
                            UML kind: uml:Package */
                            package 'L2.2.1.1_Ground Segment Behaviors' {
                                doc /* Source XMI: _19_0_2_3880181_1562510825322_726032_62215
                                Comment _19_0_2_3880181_1601214540452_938602_62971
                                Repository for Ground Segment behaviors.  To be populated by a mission-specific team
                                UML kind: uml:Package */
                                package 'Ground Segment Behavior A' {
                                    doc /* Source XMI: _19_0_2_3880181_1572631229733_603212_64649
                                    Comment _19_0_2_3880181_1601214900957_121078_62972
                                    Example / placeholder / template for Ground Segment Behaviors
                                    UML kind: uml:Package */
                                    dependency relationship_1 from OfficialCSRM::'Data'::'01 - CubeSat System Reference Model'::'5 - Architecture'::'L2_Segment'::'L2.2_Ground Segment'::'L2.2.1_Behaviors'::'L2.2.1.1_Ground Segment Behaviors'::'Ground Segment Behavior A' to OfficialCSRM::'Data'::'01 - CubeSat System Reference Model'::'4 - Requirements'::'L2 Segment Rqts'::'L2.2 Ground Segment Rqts'::'Ground Segment Rqts Group'::'Ground Segment Requirement A' {
                                        doc /* Source XMI: _19_0_2_3880181_1572709204505_309038_63652
                                        Stereotype Refine
                                        UML kind: uml:Abstraction */
                                    }
                                }
                            }
                            package 'L2.2.1.2_Ground Segment Use Cases' {
                                doc /* Source XMI: _19_0_2_3880181_1570453799430_48392_62466
                                Comment _19_0_2_3880181_1601215276449_522580_62977
                                Repository for Ground Segment use cases.  To be populated by a mission-specific team
                                UML kind: uml:Package */
                                package 'Ground Segment Use Case A' {
                                    doc /* Source XMI: _19_0_2_3880181_1572706119424_223473_63221
                                    Comment _19_0_2_3880181_1601215032232_855071_62973
                                    Example / placeholder / template for Ground Segment Use Cases.
                                    UML kind: uml:Package */
                                    dependency relationship_1 from OfficialCSRM::'Data'::'01 - CubeSat System Reference Model'::'5 - Architecture'::'L2_Segment'::'L2.2_Ground Segment'::'L2.2.1_Behaviors'::'L2.2.1.2_Ground Segment Use Cases'::'Ground Segment Use Case A' to OfficialCSRM::'Data'::'01 - CubeSat System Reference Model'::'5 - Architecture'::'L2_Segment'::'L2.2_Ground Segment'::'L2.2.1_Behaviors'::'L2.2.1.1_Ground Segment Behaviors'::'Ground Segment Behavior A' {
                                        doc /* Source XMI: _19_0_2_3880181_1637079420922_580936_55597
                                        Stereotype Refine
                                        UML kind: uml:Abstraction */
                                    }
                                }
                            }
                            package 'L2.2.1.3_Ground Segment Activities' {
                                doc /* Source XMI: _19_0_2_3880181_1570453632324_230097_62315
                                Comment _19_0_2_3880181_1601215322396_578025_62978
                                Repository for Ground Segment activities.  To be populated by a mission-specific team
                                UML kind: uml:Package */
                                package 'Ground Segment Activity A' {
                                    doc /* Source XMI: _19_0_2_3880181_1572631012199_666044_64589
                                    Comment _19_0_2_3880181_1601215158020_877393_62975
                                    Example / placeholder / template for Ground Segment Activities.
                                    UML kind: uml:Package */
                                    action def 'Ground Segment Activity A' {
                                        doc /* Source XMI: _19_0_2_3880181_1572706262396_772931_63229
                                        UML kind: uml:Activity */
                                    }
                                    dependency relationship_2 from OfficialCSRM::'Data'::'01 - CubeSat System Reference Model'::'5 - Architecture'::'L2_Segment'::'L2.2_Ground Segment'::'L2.2.1_Behaviors'::'L2.2.1.3_Ground Segment Activities'::'Ground Segment Activity A' to OfficialCSRM::'Data'::'01 - CubeSat System Reference Model'::'5 - Architecture'::'L2_Segment'::'L2.2_Ground Segment'::'L2.2.1_Behaviors'::'L2.2.1.2_Ground Segment Use Cases'::'Ground Segment Use Case A' {
                                        doc /* Source XMI: _19_0_2_3880181_1572706677034_948380_63271
                                        Stereotype Refine
                                        UML kind: uml:Abstraction */
                                    }
                                }
                            }
                        }
                    }
                    package 'L2.1_Space Segment' {
                        doc /* Source XMI: _18_0_6_3e4019a_1472151552165_867423_13480
                        Comment _19_0_2_3880181_1600891944781_192705_62865
                        Package of Space Segment behaviors and structures.
                        The CubeSat Space Segment consists of one or more CubeSats with their orbits and subsystems.
                        The Space Segment includes designs, interfaces, and operations to comply with the Rqts and constraints of the Transport, Launch, and Deploy Services.
                        UML kind: uml:Package */
                        package 'L2.1.1_Behaviors' {
                            doc /* Source XMI: _18_0_6_3e4019a_1472151563826_413557_14070
                            Comment _19_0_2_3880181_1600969957681_101441_62709
                            Package of CubeSat behaviors. use cases, and activities.  For population by a mission-specific team.
                            UML kind: uml:Package */
                            package 'L2.1.1.1_CubeSat Behaviors' {
                                doc /* Source XMI: _19_0_2_3880181_1562510508337_339000_61844
                                Comment _19_0_2_3880181_1600970096960_596701_62711
                                Repository for CubeSat behaviors.  To be populated by a mission-specific team.
                                UML kind: uml:Package */
                                package 'CubeSat Behavior A' {
                                    doc /* Source XMI: _19_0_2_3880181_1572629267256_386647_64274
                                    Comment _19_0_2_3880181_1601213363888_277309_62952
                                    Example / placeholder / template for Cubesat Behaviors
                                    UML kind: uml:Package */
                                    dependency relationship_1 from OfficialCSRM::'Data'::'01 - CubeSat System Reference Model'::'5 - Architecture'::'L2_Segment'::'L2.1_Space Segment'::'L2.1.1_Behaviors'::'L2.1.1.1_CubeSat Behaviors'::'CubeSat Behavior A' to OfficialCSRM::'Data'::'01 - CubeSat System Reference Model'::'4 - Requirements'::'L2 Segment Rqts'::'L2.1 Space Segment Rqts'::'L2.1.1 CubeSat Rqts'::'CubeSat Rqts Group'::'Requirement Name' {
                                        doc /* Source XMI: _19_0_2_3880181_1636990696334_418893_56351
                                        Stereotype Refine
                                        UML kind: uml:Abstraction */
                                    }
                                }
                            }
                            package 'L2.1.1.3_CubeSat Activities' {
                                doc /* Source XMI: _19_0_2_3880181_1570451526573_45973_62691
                                Comment _19_0_2_3880181_1600970224828_597686_62713
                                The repository for CubeSat activities.  To be populated by a mission specific team.
                                UML kind: uml:Package */
                                package 'CubeSat Activity A' {
                                    doc /* Source XMI: _19_0_2_3880181_1572628836613_180562_64043
                                    Comment _19_0_2_3880181_1601213841537_343537_62967
                                    Example / placeholder / template for Cubesat Activities
                                    UML kind: uml:Package */
                                    dependency relationship_1 from OfficialCSRM::'Data'::'01 - CubeSat System Reference Model'::'5 - Architecture'::'L2_Segment'::'L2.1_Space Segment'::'L2.1.1_Behaviors'::'L2.1.1.3_CubeSat Activities'::'CubeSat Activity A' to OfficialCSRM::'Data'::'01 - CubeSat System Reference Model'::'5 - Architecture'::'L2_Segment'::'L2.1_Space Segment'::'L2.1.1_Behaviors'::'L2.1.1.2_CubeSat Use Cases'::'CubeSat Use Case A' {
                                        doc /* Source XMI: _19_0_2_3880181_1572637564435_327592_63019
                                        Stereotype Refine
                                        UML kind: uml:Abstraction */
                                    }
                                    action def 'CubeSat Activity A' {
                                        doc /* Source XMI: _19_0_2_3880181_1637022831398_241003_55979
                                        UML kind: uml:Activity */
                                    }
                                }
                            }
                            package 'L2.1.1.2_CubeSat Use Cases' {
                                doc /* Source XMI: _19_0_2_3880181_1570451678853_796688_62770
                                Comment _19_0_2_3880181_1600970196487_423309_62712
                                The repository for CubeSat use cases.  To be populated by a mission specific team.
                                UML kind: uml:Package */
                                package 'CubeSat Use Case A' {
                                    doc /* Source XMI: _19_0_2_3880181_1572629398833_154139_64334
                                    Comment _19_0_2_3880181_1601213696049_914998_62955
                                    An example / placeholder / template for CubeSat Use Cases.
                                    UML kind: uml:Package */
                                    dependency relationship_1 from OfficialCSRM::'Data'::'01 - CubeSat System Reference Model'::'5 - Architecture'::'L2_Segment'::'L2.1_Space Segment'::'L2.1.1_Behaviors'::'L2.1.1.2_CubeSat Use Cases'::'CubeSat Use Case A' to OfficialCSRM::'Data'::'01 - CubeSat System Reference Model'::'5 - Architecture'::'L2_Segment'::'L2.1_Space Segment'::'L2.1.1_Behaviors'::'L2.1.1.1_CubeSat Behaviors'::'CubeSat Behavior A' {
                                        doc /* Source XMI: _19_0_2_3880181_1636990867380_360324_56424
                                        Stereotype Refine
                                        UML kind: uml:Abstraction */
                                    }
                                }
                            }
                        }
                        package 'L2.1.2_Structures' {
                            doc /* Source XMI: _18_0_6_3e4019a_1472151563826_919548_14071
                            Comment _19_0_2_3880181_1600969794545_245160_62708
                            Package of Space Segment structures.
                            UML kind: uml:Package */
                            part def 'Space Segment' {
                                @OfficialCSRMProfile::'Architecture Structures Profile'::'Segment';
                                doc /* Source XMI: _18_0_6_3e4019a_1472151573831_645083_14608
                                Stereotype Segment
                                Comment _18_0_6_3e4019a_1472151611931_946300_16430
                                UML kind: uml:Class */
                                part 'cubeSat' : OfficialCSRM::'Data'::'01 - CubeSat System Reference Model'::'5 - Architecture'::'L2_Segment'::'L2.1_Space Segment'::'L2.1.2_Structures'::'CubeSat' [1..*] {
                                    doc /* Source XMI: _18_5_1_3880181_1505161330774_139232_61542
                                    Stereotype PartProperty
                                    UML aggregation: composite
                                    UML association: _18_5_1_3880181_1505161330774_608607_61541
                                    Source-only uml:LiteralUnlimitedNatural _18_5_1_3880181_1505161492099_365088_61616: {"type": "uml:LiteralUnlimitedNatural", "id": "_18_5_1_3880181_1505161492099_365088_61616", "value": "*"} */
                                }
                                part 'cubeSat Orbit' : OfficialCSRM::'Data'::'01 - CubeSat System Reference Model'::'5 - Architecture'::'L2_Segment'::'L2.1_Space Segment'::'L2.1.2_Structures'::'CubeSat Orbit' [1..*] {
                                    doc /* Source XMI: _18_5_1_3880181_1505161434667_139876_61573
                                    Stereotype PartProperty
                                    UML aggregation: composite
                                    UML association: _18_5_1_3880181_1505161434667_235639_61572
                                    Source-only uml:LiteralUnlimitedNatural _18_5_1_3880181_1505161510602_973535_61622: {"type": "uml:LiteralUnlimitedNatural", "id": "_18_5_1_3880181_1505161510602_973535_61622", "value": "*"} */
                                }
                            }
                            part def 'CubeSat' {
                                @OfficialCSRMProfile::'Architecture Structures Profile'::'CubeSat';
                                doc /* Source XMI: _18_0_6_3e4019a_1472151573832_997891_14609
                                Stereotype CubeSat
                                Comment _18_4_1_3e4019a_1491498252445_368596_16620
                                UML kind: uml:Class */
                                // UML generalization _18_4_1_3880181_1492191352156_73649_45860 to MD_customization_for_SysML.mdzip#_18_3_903028d_1448291312269_537593_13833
                                attribute 'Orbit' {
                                    doc /* Source XMI: _18_4_1_3880181_1493069689424_917266_46848
                                    Stereotype ReferenceProperty
                                    UML aggregation: none
                                    UML association: none */
                                }
                                part 'mission Payload1' : OfficialCSRM::'Data'::'01 - CubeSat System Reference Model'::'5 - Architecture'::'L3_Subsystems'::'L3.1_CubeSat Subsystems'::'L3.1.2_Structures'::'Mission Payload' {
                                    doc /* Source XMI: _18_5_1_3880181_1506966495487_230824_63446
                                    Stereotype PartProperty
                                    UML aggregation: composite
                                    UML association: _18_5_1_3880181_1506966495487_52447_63445 */
                                }
                                part 'command and Data Handling Subsystem1' : OfficialCSRM::'Data'::'01 - CubeSat System Reference Model'::'5 - Architecture'::'L3_Subsystems'::'L3.1_CubeSat Subsystems'::'L3.1.2_Structures'::'Command and Data Handling Subsystem' {
                                    doc /* Source XMI: _18_5_1_3880181_1506966582896_859326_63479
                                    Stereotype PartProperty
                                    UML aggregation: composite
                                    UML association: _18_5_1_3880181_1506966582896_293556_63478 */
                                }
                                part 'communication Subsystem1' : OfficialCSRM::'Data'::'01 - CubeSat System Reference Model'::'5 - Architecture'::'L3_Subsystems'::'L3.1_CubeSat Subsystems'::'L3.1.2_Structures'::'Communication Subsystem' {
                                    doc /* Source XMI: _18_5_1_3880181_1506967003841_585015_63529
                                    Stereotype PartProperty
                                    UML aggregation: composite
                                    UML association: _18_5_1_3880181_1506967003841_19190_63528 */
                                }
                                part 'attitude Determination and Control Subsystem1' : OfficialCSRM::'Data'::'01 - CubeSat System Reference Model'::'5 - Architecture'::'L3_Subsystems'::'L3.1_CubeSat Subsystems'::'L3.1.2_Structures'::'Attitude Determination and Control Subsystem' {
                                    doc /* Source XMI: _18_5_1_3880181_1506967218373_193109_63589
                                    Stereotype PartProperty
                                    UML aggregation: composite
                                    UML association: _18_5_1_3880181_1506967218373_412660_63588 */
                                }
                                part 'guidance Navigation and Control Subsystem' : OfficialCSRM::'Data'::'01 - CubeSat System Reference Model'::'5 - Architecture'::'L3_Subsystems'::'L3.1_CubeSat Subsystems'::'L3.1.2_Structures'::'Guidance Navigation and Control Subsystem' {
                                    doc /* Source XMI: _18_5_1_3880181_1506967281666_252088_63619
                                    Stereotype PartProperty
                                    UML aggregation: composite
                                    UML association: _18_5_1_3880181_1506967281666_243398_63618 */
                                }
                                part 'structures and Mechanisms Subsystem1' : OfficialCSRM::'Data'::'01 - CubeSat System Reference Model'::'5 - Architecture'::'L3_Subsystems'::'L3.1_CubeSat Subsystems'::'L3.1.2_Structures'::'Structures and Mechanisms Subsystem' {
                                    doc /* Source XMI: _18_5_1_3880181_1506967335052_176911_63649
                                    Stereotype PartProperty
                                    UML aggregation: composite
                                    UML association: _18_5_1_3880181_1506967335052_789344_63648 */
                                }
                                part 'power Subsystem1' : OfficialCSRM::'Data'::'01 - CubeSat System Reference Model'::'5 - Architecture'::'L3_Subsystems'::'L3.1_CubeSat Subsystems'::'L3.1.2_Structures'::'Power Subsystem' {
                                    doc /* Source XMI: _18_5_1_3880181_1506967716770_36116_63837
                                    Stereotype PartProperty
                                    UML aggregation: composite
                                    UML association: _18_5_1_3880181_1506967716770_907777_63836 */
                                }
                                part 'propulsion Subsystem1' : OfficialCSRM::'Data'::'01 - CubeSat System Reference Model'::'5 - Architecture'::'L3_Subsystems'::'L3.1_CubeSat Subsystems'::'L3.1.2_Structures'::'Propulsion Subsystem' {
                                    doc /* Source XMI: _18_5_1_3880181_1506967809287_3062_63919
                                    Stereotype PartProperty
                                    UML aggregation: composite
                                    UML association: _18_5_1_3880181_1506967809287_648878_63918 */
                                }
                                part 'thermal Subsystem1' : OfficialCSRM::'Data'::'01 - CubeSat System Reference Model'::'5 - Architecture'::'L3_Subsystems'::'L3.1_CubeSat Subsystems'::'L3.1.2_Structures'::'Thermal Subsystem' {
                                    doc /* Source XMI: _18_5_1_3880181_1506967837292_646407_63949
                                    Stereotype PartProperty
                                    UML aggregation: composite
                                    UML association: _18_5_1_3880181_1506967837292_718711_63948 */
                                }
                            }
                            part def 'CubeSat Orbit' {
                                doc /* Source XMI: _18_4_1_3880181_1493069636897_942758_46779
                                Stereotype Block
                                UML kind: uml:Class */
                                attribute 'eccentricity' {
                                    doc /* Source XMI: _18_4_1_3880181_1493069880918_113410_46878
                                    Stereotype ValueProperty
                                    UML aggregation: composite
                                    UML association: none */
                                }
                                attribute 'semi-major axis' {
                                    doc /* Source XMI: _18_4_1_3880181_1493069921026_929169_46883
                                    Stereotype ValueProperty
                                    UML aggregation: composite
                                    UML association: none */
                                }
                                attribute 'inclination' {
                                    doc /* Source XMI: _18_4_1_3880181_1493069957335_626744_46888
                                    Stereotype ValueProperty
                                    UML aggregation: composite
                                    UML association: none */
                                }
                                attribute 'longitude of ascending node' {
                                    doc /* Source XMI: _18_4_1_3880181_1493069977412_427271_46893
                                    Stereotype ValueProperty
                                    UML aggregation: composite
                                    UML association: none */
                                }
                                attribute 'argument of perigee' {
                                    doc /* Source XMI: _18_4_1_3880181_1493070051201_759392_46898
                                    Stereotype ValueProperty
                                    UML aggregation: composite
                                    UML association: none */
                                }
                                attribute 'true anomaly at epoch' {
                                    doc /* Source XMI: _18_4_1_3880181_1493070088062_252284_46903
                                    Stereotype ValueProperty
                                    UML aggregation: composite
                                    UML association: none */
                                }
                                attribute 'time of epoch' {
                                    doc /* Source XMI: _18_4_1_3880181_1493070115383_505128_46908
                                    Stereotype ValueProperty
                                    UML aggregation: composite
                                    UML association: none */
                                }
                            }
                            connection def association_4 {
                                doc /* Source XMI: _18_5_1_3880181_1505161330774_608607_61541
                                UML end details are in the source map (SysML v2 connector ends have fixed [1..1] multiplicity). */
                                end end1 : OfficialCSRM::'Data'::'01 - CubeSat System Reference Model'::'5 - Architecture'::'L2_Segment'::'L2.1_Space Segment'::'L2.1.2_Structures'::'CubeSat' {
                                    doc /* Source XMI: _18_5_1_3880181_1505161330774_139232_61542
                                    Stereotype PartProperty
                                    UML end name: cubeSat
                                    Source-only uml:LiteralUnlimitedNatural _18_5_1_3880181_1505161492099_365088_61616: {"type": "uml:LiteralUnlimitedNatural", "id": "_18_5_1_3880181_1505161492099_365088_61616", "value": "*"} */
                                }
                                end end2 : OfficialCSRM::'Data'::'01 - CubeSat System Reference Model'::'5 - Architecture'::'L2_Segment'::'L2.1_Space Segment'::'L2.1.2_Structures'::'Space Segment' {
                                    doc /* Source XMI: _18_5_1_3880181_1505161330774_6899_61543
                                    UML end name: (unnamed) */
                                }
                            }
                            connection def association_5 {
                                doc /* Source XMI: _18_5_1_3880181_1505161434667_235639_61572
                                UML end details are in the source map (SysML v2 connector ends have fixed [1..1] multiplicity). */
                                end end1 : OfficialCSRM::'Data'::'01 - CubeSat System Reference Model'::'5 - Architecture'::'L2_Segment'::'L2.1_Space Segment'::'L2.1.2_Structures'::'CubeSat Orbit' {
                                    doc /* Source XMI: _18_5_1_3880181_1505161434667_139876_61573
                                    Stereotype PartProperty
                                    UML end name: cubeSat Orbit
                                    Source-only uml:LiteralUnlimitedNatural _18_5_1_3880181_1505161510602_973535_61622: {"type": "uml:LiteralUnlimitedNatural", "id": "_18_5_1_3880181_1505161510602_973535_61622", "value": "*"} */
                                }
                                end end2 : OfficialCSRM::'Data'::'01 - CubeSat System Reference Model'::'5 - Architecture'::'L2_Segment'::'L2.1_Space Segment'::'L2.1.2_Structures'::'Space Segment' {
                                    doc /* Source XMI: _18_5_1_3880181_1505161434667_537718_61574
                                    UML end name: (unnamed) */
                                }
                            }
                            connection def association_6 {
                                doc /* Source XMI: _18_5_1_3880181_1506966495487_52447_63445
                                UML end details are in the source map (SysML v2 connector ends have fixed [1..1] multiplicity). */
                                end end1 : OfficialCSRM::'Data'::'01 - CubeSat System Reference Model'::'5 - Architecture'::'L3_Subsystems'::'L3.1_CubeSat Subsystems'::'L3.1.2_Structures'::'Mission Payload' {
                                    doc /* Source XMI: _18_5_1_3880181_1506966495487_230824_63446
                                    Stereotype PartProperty
                                    UML end name: mission Payload1 */
                                }
                                end end2 : OfficialCSRM::'Data'::'01 - CubeSat System Reference Model'::'5 - Architecture'::'L2_Segment'::'L2.1_Space Segment'::'L2.1.2_Structures'::'CubeSat' {
                                    doc /* Source XMI: _18_5_1_3880181_1506966495487_431599_63447
                                    UML end name: (unnamed) */
                                }
                            }
                            connection def association_7 {
                                doc /* Source XMI: _18_5_1_3880181_1506966582896_293556_63478
                                UML end details are in the source map (SysML v2 connector ends have fixed [1..1] multiplicity). */
                                end end1 : OfficialCSRM::'Data'::'01 - CubeSat System Reference Model'::'5 - Architecture'::'L3_Subsystems'::'L3.1_CubeSat Subsystems'::'L3.1.2_Structures'::'Command and Data Handling Subsystem' {
                                    doc /* Source XMI: _18_5_1_3880181_1506966582896_859326_63479
                                    Stereotype PartProperty
                                    UML end name: command and Data Handling Subsystem1 */
                                }
                                end end2 : OfficialCSRM::'Data'::'01 - CubeSat System Reference Model'::'5 - Architecture'::'L2_Segment'::'L2.1_Space Segment'::'L2.1.2_Structures'::'CubeSat' {
                                    doc /* Source XMI: _18_5_1_3880181_1506966582896_419193_63480
                                    UML end name: (unnamed) */
                                }
                            }
                            connection def association_8 {
                                doc /* Source XMI: _18_5_1_3880181_1506967003841_19190_63528
                                UML end details are in the source map (SysML v2 connector ends have fixed [1..1] multiplicity). */
                                end end1 : OfficialCSRM::'Data'::'01 - CubeSat System Reference Model'::'5 - Architecture'::'L3_Subsystems'::'L3.1_CubeSat Subsystems'::'L3.1.2_Structures'::'Communication Subsystem' {
                                    doc /* Source XMI: _18_5_1_3880181_1506967003841_585015_63529
                                    Stereotype PartProperty
                                    UML end name: communication Subsystem1 */
                                }
                                end end2 : OfficialCSRM::'Data'::'01 - CubeSat System Reference Model'::'5 - Architecture'::'L2_Segment'::'L2.1_Space Segment'::'L2.1.2_Structures'::'CubeSat' {
                                    doc /* Source XMI: _18_5_1_3880181_1506967003841_846173_63530
                                    UML end name: (unnamed) */
                                }
                            }
                            connection def association_9 {
                                doc /* Source XMI: _18_5_1_3880181_1506967218373_412660_63588
                                UML end details are in the source map (SysML v2 connector ends have fixed [1..1] multiplicity). */
                                end end1 : OfficialCSRM::'Data'::'01 - CubeSat System Reference Model'::'5 - Architecture'::'L3_Subsystems'::'L3.1_CubeSat Subsystems'::'L3.1.2_Structures'::'Attitude Determination and Control Subsystem' {
                                    doc /* Source XMI: _18_5_1_3880181_1506967218373_193109_63589
                                    Stereotype PartProperty
                                    UML end name: attitude Determination and Control Subsystem1 */
                                }
                                end end2 : OfficialCSRM::'Data'::'01 - CubeSat System Reference Model'::'5 - Architecture'::'L2_Segment'::'L2.1_Space Segment'::'L2.1.2_Structures'::'CubeSat' {
                                    doc /* Source XMI: _18_5_1_3880181_1506967218389_745691_63590
                                    UML end name: (unnamed) */
                                }
                            }
                            connection def association_10 {
                                doc /* Source XMI: _18_5_1_3880181_1506967281666_243398_63618
                                UML end details are in the source map (SysML v2 connector ends have fixed [1..1] multiplicity). */
                                end end1 : OfficialCSRM::'Data'::'01 - CubeSat System Reference Model'::'5 - Architecture'::'L3_Subsystems'::'L3.1_CubeSat Subsystems'::'L3.1.2_Structures'::'Guidance Navigation and Control Subsystem' {
                                    doc /* Source XMI: _18_5_1_3880181_1506967281666_252088_63619
                                    Stereotype PartProperty
                                    UML end name: guidance Navigation and Control Subsystem */
                                }
                                end end2 : OfficialCSRM::'Data'::'01 - CubeSat System Reference Model'::'5 - Architecture'::'L2_Segment'::'L2.1_Space Segment'::'L2.1.2_Structures'::'CubeSat' {
                                    doc /* Source XMI: _18_5_1_3880181_1506967281666_404009_63620
                                    UML end name: (unnamed) */
                                }
                            }
                            connection def association_11 {
                                doc /* Source XMI: _18_5_1_3880181_1506967335052_789344_63648
                                UML end details are in the source map (SysML v2 connector ends have fixed [1..1] multiplicity). */
                                end end1 : OfficialCSRM::'Data'::'01 - CubeSat System Reference Model'::'5 - Architecture'::'L3_Subsystems'::'L3.1_CubeSat Subsystems'::'L3.1.2_Structures'::'Structures and Mechanisms Subsystem' {
                                    doc /* Source XMI: _18_5_1_3880181_1506967335052_176911_63649
                                    Stereotype PartProperty
                                    UML end name: structures and Mechanisms Subsystem1 */
                                }
                                end end2 : OfficialCSRM::'Data'::'01 - CubeSat System Reference Model'::'5 - Architecture'::'L2_Segment'::'L2.1_Space Segment'::'L2.1.2_Structures'::'CubeSat' {
                                    doc /* Source XMI: _18_5_1_3880181_1506967335052_713771_63650
                                    UML end name: (unnamed) */
                                }
                            }
                            connection def association_12 {
                                doc /* Source XMI: _18_5_1_3880181_1506967716770_907777_63836
                                UML end details are in the source map (SysML v2 connector ends have fixed [1..1] multiplicity). */
                                end end1 : OfficialCSRM::'Data'::'01 - CubeSat System Reference Model'::'5 - Architecture'::'L3_Subsystems'::'L3.1_CubeSat Subsystems'::'L3.1.2_Structures'::'Power Subsystem' {
                                    doc /* Source XMI: _18_5_1_3880181_1506967716770_36116_63837
                                    Stereotype PartProperty
                                    UML end name: power Subsystem1 */
                                }
                                end end2 : OfficialCSRM::'Data'::'01 - CubeSat System Reference Model'::'5 - Architecture'::'L2_Segment'::'L2.1_Space Segment'::'L2.1.2_Structures'::'CubeSat' {
                                    doc /* Source XMI: _18_5_1_3880181_1506967716770_49565_63838
                                    UML end name: (unnamed) */
                                }
                            }
                            connection def association_13 {
                                doc /* Source XMI: _18_5_1_3880181_1506967809287_648878_63918
                                UML end details are in the source map (SysML v2 connector ends have fixed [1..1] multiplicity). */
                                end end1 : OfficialCSRM::'Data'::'01 - CubeSat System Reference Model'::'5 - Architecture'::'L3_Subsystems'::'L3.1_CubeSat Subsystems'::'L3.1.2_Structures'::'Propulsion Subsystem' {
                                    doc /* Source XMI: _18_5_1_3880181_1506967809287_3062_63919
                                    Stereotype PartProperty
                                    UML end name: propulsion Subsystem1 */
                                }
                                end end2 : OfficialCSRM::'Data'::'01 - CubeSat System Reference Model'::'5 - Architecture'::'L2_Segment'::'L2.1_Space Segment'::'L2.1.2_Structures'::'CubeSat' {
                                    doc /* Source XMI: _18_5_1_3880181_1506967809287_211643_63920
                                    UML end name: (unnamed) */
                                }
                            }
                            connection def association_14 {
                                doc /* Source XMI: _18_5_1_3880181_1506967837292_718711_63948
                                UML end details are in the source map (SysML v2 connector ends have fixed [1..1] multiplicity). */
                                end end1 : OfficialCSRM::'Data'::'01 - CubeSat System Reference Model'::'5 - Architecture'::'L3_Subsystems'::'L3.1_CubeSat Subsystems'::'L3.1.2_Structures'::'Thermal Subsystem' {
                                    doc /* Source XMI: _18_5_1_3880181_1506967837292_646407_63949
                                    Stereotype PartProperty
                                    UML end name: thermal Subsystem1 */
                                }
                                end end2 : OfficialCSRM::'Data'::'01 - CubeSat System Reference Model'::'5 - Architecture'::'L2_Segment'::'L2.1_Space Segment'::'L2.1.2_Structures'::'CubeSat' {
                                    doc /* Source XMI: _18_5_1_3880181_1506967837292_574830_63950
                                    UML end name: (unnamed) */
                                }
                            }
                        }
                    }
                }
                package 'L1_Enterprise' {
                    doc /* Source XMI: _18_0_6_3e4019a_1472151507105_273639_12340
                    Comment _19_0_2_3880181_1600786942217_286145_62948
                    Package of Enterprise behaviors and structures.
                    Enterprise is an aggregation of systems and users that work together to accomplish a goal.
                    At its most basic the CubeSat Mission Enterprise consists of the CubeSat Space Segment and the CubeSat Ground Segment.
                    UML kind: uml:Package */
                    package 'L1.1_Behaviors' {
                        doc /* Source XMI: _18_0_6_3e4019a_1472151550320_975483_13450
                        Comment _19_0_2_3880181_1600965146278_515474_62596
                        The package of Enterprise behaviors, use cases, and activities.
                        UML kind: uml:Package */
                        package 'L1.1.1_Enterprise Behaviors' {
                            doc /* Source XMI: _19_0_2_3880181_1562509983855_895106_61747
                            Comment _19_0_2_3880181_1600965251244_103561_62597
                            The respository for Enterprise behaviors.  To be populated by a mission specific team.
                            UML kind: uml:Package */
                            package 'Enterprise Behavior A' {
                                doc /* Source XMI: _19_0_2_3880181_1562588578131_116320_61858
                                Comment _19_0_2_3880181_1601146954828_393181_62609
                                An example / placeholder / template for  Enterprise Behaviors
                                UML kind: uml:Package */
                                dependency relationship_1 from OfficialCSRM::'Data'::'01 - CubeSat System Reference Model'::'5 - Architecture'::'L1_Enterprise'::'L1.1_Behaviors'::'L1.1.1_Enterprise Behaviors'::'Enterprise Behavior A' to OfficialCSRM::'Data'::'01 - CubeSat System Reference Model'::'1 - Stakeholders'::'1.2 Mission Stakeholders'::'1.2.6 - Mission Rqts'::'Mission Rqts Group'::'Requirement Name' {
                                    doc /* Source XMI: _19_0_2_3880181_1636988494896_445225_55870
                                    Stereotype Refine
                                    UML kind: uml:Abstraction */
                                }
                            }
                        }
                        package 'L1.1.3_Enterprise Activities' {
                            doc /* Source XMI: _19_0_2_3880181_1570449932770_835832_61787
                            Comment _19_0_2_3880181_1600965425828_824974_62600
                            The repository for Enterprise activities.  To be populated by a mission specific team.
                            UML kind: uml:Package */
                            package 'Enterprise Activity A' {
                                doc /* Source XMI: _19_0_2_3880181_1572617544730_457514_62980
                                Comment _19_0_2_3880181_1601147180380_675398_62611
                                An example / placeholder / template for Enterprise Activities
                                UML kind: uml:Package */
                                action def 'Enterprise Activity A' {
                                    doc /* Source XMI: _19_0_2_3880181_1572626019069_530286_62956
                                    UML kind: uml:Activity */
                                }
                                dependency relationship_2 from OfficialCSRM::'Data'::'01 - CubeSat System Reference Model'::'5 - Architecture'::'L1_Enterprise'::'L1.1_Behaviors'::'L1.1.3_Enterprise Activities'::'Enterprise Activity A' to OfficialCSRM::'Data'::'01 - CubeSat System Reference Model'::'5 - Architecture'::'L1_Enterprise'::'L1.1_Behaviors'::'L1.1.2_Enterprise Use Cases'::'Enterprise Use Case A' {
                                    doc /* Source XMI: _19_0_2_3880181_1636988791799_926775_55910
                                    Stereotype Refine
                                    UML kind: uml:Abstraction */
                                }
                            }
                        }
                        package 'L1.1.2_Enterprise Use Cases' {
                            doc /* Source XMI: _19_0_2_3880181_1570449962395_866561_61788
                            Comment _19_0_2_3880181_1600965339013_235205_62598
                            The repository for Enterprise use cases.  To be populated by a mission specific team.
                            UML kind: uml:Package */
                            package 'Enterprise Use Case A' {
                                doc /* Source XMI: _19_0_2_3880181_1572617669937_225277_62982
                                Comment _19_0_2_3880181_1601147067517_783352_62610
                                An example / placeholder / template for Enterprise Use Cases
                                UML kind: uml:Package */
                                dependency relationship_1 from OfficialCSRM::'Data'::'01 - CubeSat System Reference Model'::'5 - Architecture'::'L1_Enterprise'::'L1.1_Behaviors'::'L1.1.2_Enterprise Use Cases'::'Enterprise Use Case A' to OfficialCSRM::'Data'::'01 - CubeSat System Reference Model'::'5 - Architecture'::'L1_Enterprise'::'L1.1_Behaviors'::'L1.1.1_Enterprise Behaviors'::'Enterprise Behavior A' {
                                    doc /* Source XMI: _19_0_2_3880181_1636988725721_727615_55891
                                    Stereotype Refine
                                    UML kind: uml:Abstraction */
                                }
                            }
                        }
                    }
                    package 'L1.2_Structures' {
                        doc /* Source XMI: _18_0_6_3e4019a_1472151550321_803970_13451
                        Comment _19_0_2_3880181_1600969119665_973764_62667
                        The package of Enterprise structures.
                        UML kind: uml:Package */
                        part def 'CubeSat Mission Enterprise' {
                            doc /* Source XMI: _18_0_6_3e4019a_1472151562270_394124_14029
                            Stereotype Block
                            UML kind: uml:Class */
                            part 'ground Station Services' : OfficialCSRM::'Data'::'01 - CubeSat System Reference Model'::'5 - Architecture'::'L1_Enterprise'::'L1.2_Structures'::'Ground Station Services' {
                                doc /* Source XMI: _18_5_1_3880181_1504905655515_133676_57431
                                Stereotype PartProperty
                                UML aggregation: composite
                                UML association: _18_5_1_3880181_1504905655515_174763_57430 */
                            }
                            part 'property_1' : OfficialCSRM::'Data'::'01 - CubeSat System Reference Model'::'5 - Architecture'::'L1_Enterprise'::'L1.2_Structures'::'Transport, Launch, and Deploy Services' {
                                doc /* Source XMI: _18_5_1_3880181_1504905667157_847180_57462
                                Stereotype PartProperty
                                UML aggregation: composite
                                UML association: _18_5_1_3880181_1504905667157_874750_57461 */
                            }
                            part 'space Segment' : OfficialCSRM::'Data'::'01 - CubeSat System Reference Model'::'5 - Architecture'::'L2_Segment'::'L2.1_Space Segment'::'L2.1.2_Structures'::'Space Segment' {
                                doc /* Source XMI: _18_5_1_3880181_1504907200801_528658_58027
                                Stereotype PartProperty
                                UML aggregation: composite
                                UML association: _18_5_1_3880181_1504907200801_906314_58026 */
                            }
                            part 'ground Segment' : OfficialCSRM::'Data'::'01 - CubeSat System Reference Model'::'5 - Architecture'::'L2_Segment'::'L2.2_Ground Segment'::'L2.2.2_Structures'::'Ground Segment' {
                                doc /* Source XMI: _18_5_1_3880181_1504907579177_901684_58228
                                Stereotype PartProperty
                                UML aggregation: composite
                                UML association: _18_5_1_3880181_1504907579177_641841_58227 */
                            }
                            part 'GPS' : OfficialCSRM::'Data'::'01 - CubeSat System Reference Model'::'5 - Architecture'::'L1_Enterprise'::'L1.2_Structures'::'GNSS' {
                                doc /* Source XMI: _18_5_1_3880181_1505138455773_514516_58522
                                Stereotype PartProperty
                                UML aggregation: composite
                                UML association: _18_5_1_3880181_1505138455773_415075_58521 */
                            }
                        }
                        part def 'Ground Station Services' {
                            doc /* Source XMI: _18_0_6_3e4019a_1472151562277_880588_14035
                            Stereotype Block
                            UML kind: uml:Class */
                        }
                        part def 'Transport, Launch, and Deploy Services' {
                            doc /* Source XMI: _18_0_6_3e4019a_1472151562278_614914_14036
                            Stereotype Block
                            UML kind: uml:Class */
                        }
                        part def 'GNSS' {
                            doc /* Source XMI: _18_4_1_3e4019a_1491499001976_92565_16953
                            Stereotype Block
                            UML kind: uml:Class */
                        }
                        connection def association_5 {
                            doc /* Source XMI: _18_5_1_3880181_1504905655515_174763_57430
                            UML end details are in the source map (SysML v2 connector ends have fixed [1..1] multiplicity). */
                            end end1 : OfficialCSRM::'Data'::'01 - CubeSat System Reference Model'::'5 - Architecture'::'L1_Enterprise'::'L1.2_Structures'::'Ground Station Services' {
                                doc /* Source XMI: _18_5_1_3880181_1504905655515_133676_57431
                                Stereotype PartProperty
                                UML end name: ground Station Services */
                            }
                            end end2 : OfficialCSRM::'Data'::'01 - CubeSat System Reference Model'::'5 - Architecture'::'L1_Enterprise'::'L1.2_Structures'::'CubeSat Mission Enterprise' {
                                doc /* Source XMI: _18_5_1_3880181_1504905655515_829862_57432
                                UML end name: (unnamed) */
                            }
                        }
                        connection def association_6 {
                            doc /* Source XMI: _18_5_1_3880181_1504905667157_874750_57461
                            UML end details are in the source map (SysML v2 connector ends have fixed [1..1] multiplicity). */
                            end end1 : OfficialCSRM::'Data'::'01 - CubeSat System Reference Model'::'5 - Architecture'::'L1_Enterprise'::'L1.2_Structures'::'Transport, Launch, and Deploy Services' {
                                doc /* Source XMI: _18_5_1_3880181_1504905667157_847180_57462
                                Stereotype PartProperty
                                UML end name: (unnamed) */
                            }
                            end end2 : OfficialCSRM::'Data'::'01 - CubeSat System Reference Model'::'5 - Architecture'::'L1_Enterprise'::'L1.2_Structures'::'CubeSat Mission Enterprise' {
                                doc /* Source XMI: _18_5_1_3880181_1504905667157_577651_57463
                                UML end name: (unnamed) */
                            }
                        }
                        connection def association_7 {
                            doc /* Source XMI: _18_5_1_3880181_1504907200801_906314_58026
                            UML end details are in the source map (SysML v2 connector ends have fixed [1..1] multiplicity). */
                            end end1 : OfficialCSRM::'Data'::'01 - CubeSat System Reference Model'::'5 - Architecture'::'L2_Segment'::'L2.1_Space Segment'::'L2.1.2_Structures'::'Space Segment' {
                                doc /* Source XMI: _18_5_1_3880181_1504907200801_528658_58027
                                Stereotype PartProperty
                                UML end name: space Segment */
                            }
                            end end2 : OfficialCSRM::'Data'::'01 - CubeSat System Reference Model'::'5 - Architecture'::'L1_Enterprise'::'L1.2_Structures'::'CubeSat Mission Enterprise' {
                                doc /* Source XMI: _18_5_1_3880181_1504907200801_149673_58028
                                UML end name: (unnamed) */
                            }
                        }
                        connection def association_8 {
                            doc /* Source XMI: _18_5_1_3880181_1504907579177_641841_58227
                            UML end details are in the source map (SysML v2 connector ends have fixed [1..1] multiplicity). */
                            end end1 : OfficialCSRM::'Data'::'01 - CubeSat System Reference Model'::'5 - Architecture'::'L2_Segment'::'L2.2_Ground Segment'::'L2.2.2_Structures'::'Ground Segment' {
                                doc /* Source XMI: _18_5_1_3880181_1504907579177_901684_58228
                                Stereotype PartProperty
                                UML end name: ground Segment */
                            }
                            end end2 : OfficialCSRM::'Data'::'01 - CubeSat System Reference Model'::'5 - Architecture'::'L1_Enterprise'::'L1.2_Structures'::'CubeSat Mission Enterprise' {
                                doc /* Source XMI: _18_5_1_3880181_1504907579177_84815_58229
                                UML end name: (unnamed) */
                            }
                        }
                        connection def association_9 {
                            doc /* Source XMI: _18_5_1_3880181_1505138455773_415075_58521
                            UML end details are in the source map (SysML v2 connector ends have fixed [1..1] multiplicity). */
                            end end1 : OfficialCSRM::'Data'::'01 - CubeSat System Reference Model'::'5 - Architecture'::'L1_Enterprise'::'L1.2_Structures'::'GNSS' {
                                doc /* Source XMI: _18_5_1_3880181_1505138455773_514516_58522
                                Stereotype PartProperty
                                UML end name: GPS */
                            }
                            end end2 : OfficialCSRM::'Data'::'01 - CubeSat System Reference Model'::'5 - Architecture'::'L1_Enterprise'::'L1.2_Structures'::'CubeSat Mission Enterprise' {
                                doc /* Source XMI: _18_5_1_3880181_1505138455789_449794_58523
                                UML end name: (unnamed) */
                            }
                        }
                    }
                }
                package 'Facilities' {
                    doc /* Source XMI: _19_0_2_3880181_1572366612023_784480_62636
                    Comment _19_0_2_3880181_1600786764963_372812_62906
                    A mission-specific team will populate the Facilities package with facilities, equipment, properties, and part relationships
                    Comment _19_0_3_2b0010b_1619534803756_870829_15147 (Explanation)
                    Just a start at how to accommodate Faciliities
                    The mission-specific team will populate the Facilities package with facilities, equipment, properties, and part relationships
                    UML kind: uml:Package */
                    part def 'Development Facility' {
                        @OfficialCSRMProfile::'Architecture Structures Profile'::'Facility';
                        doc /* Source XMI: _19_0_2_3880181_1572366846804_193851_62673
                        Stereotype Facility
                        UML kind: uml:Class */
                        part 'design Facility' : OfficialCSRM::'Data'::'01 - CubeSat System Reference Model'::'5 - Architecture'::'Facilities'::'Design Facility' {
                            doc /* Source XMI: _19_0_2_3880181_1572367108132_280327_62830
                            Stereotype PartProperty
                            UML aggregation: composite
                            UML association: _19_0_2_3880181_1572367108132_719887_62829 */
                        }
                        part 'production Facility' : OfficialCSRM::'Data'::'01 - CubeSat System Reference Model'::'5 - Architecture'::'Facilities'::'Production Facility' {
                            doc /* Source XMI: _19_0_2_3880181_1572367594212_695440_62998
                            Stereotype PartProperty
                            UML aggregation: composite
                            UML association: _19_0_2_3880181_1572367594212_876766_62997 */
                        }
                        part 'integration Facility' : OfficialCSRM::'Data'::'01 - CubeSat System Reference Model'::'5 - Architecture'::'Facilities'::'Integration Facility' {
                            doc /* Source XMI: _19_0_2_3880181_1572369275230_579235_63283
                            Stereotype PartProperty
                            UML aggregation: composite
                            UML association: _19_0_2_3880181_1572369275230_602679_63282 */
                        }
                        part 'test Facility' : OfficialCSRM::'Data'::'01 - CubeSat System Reference Model'::'5 - Architecture'::'Facilities'::'Test Facility' {
                            doc /* Source XMI: _19_0_2_3880181_1572378692581_314229_63172
                            Stereotype PartProperty
                            UML aggregation: composite
                            UML association: _19_0_2_3880181_1572378692581_144207_63171 */
                        }
                    }
                    part def 'Operations Facility' {
                        @OfficialCSRMProfile::'Architecture Structures Profile'::'Facility';
                        doc /* Source XMI: _19_0_2_3880181_1572366903726_638065_62711
                        Stereotype Facility
                        UML kind: uml:Class */
                    }
                    part def 'Design Facility' {
                        @OfficialCSRMProfile::'Architecture Structures Profile'::'Facility';
                        doc /* Source XMI: _19_0_2_3880181_1572366975727_175828_62749
                        Stereotype Facility
                        UML kind: uml:Class */
                        part 'offices' : OfficialCSRM::'Data'::'01 - CubeSat System Reference Model'::'5 - Architecture'::'Facilities'::'Offices' {
                            doc /* Source XMI: _19_0_2_3880181_1572368049259_232277_63226
                            Stereotype PartProperty
                            UML aggregation: composite
                            UML association: _19_0_2_3880181_1572368049259_579600_63225 */
                        }
                    }
                    part def 'Production Facility' {
                        @OfficialCSRMProfile::'Architecture Structures Profile'::'Facility';
                        doc /* Source XMI: _19_0_2_3880181_1572367018961_916810_62751
                        Stereotype Facility
                        UML kind: uml:Class */
                        part 'clean Room' : OfficialCSRM::'Data'::'01 - CubeSat System Reference Model'::'5 - Architecture'::'Facilities'::'Clean Room' {
                            doc /* Source XMI: _19_0_2_3880181_1572367605436_425348_63014
                            Stereotype PartProperty
                            UML aggregation: composite
                            UML association: _19_0_2_3880181_1572367605436_283853_63013 */
                        }
                    }
                    connection def association_6 {
                        doc /* Source XMI: _19_0_2_3880181_1572367108132_719887_62829
                        UML end details are in the source map (SysML v2 connector ends have fixed [1..1] multiplicity). */
                        end end1 : OfficialCSRM::'Data'::'01 - CubeSat System Reference Model'::'5 - Architecture'::'Facilities'::'Design Facility' {
                            doc /* Source XMI: _19_0_2_3880181_1572367108132_280327_62830
                            Stereotype PartProperty
                            UML end name: design Facility */
                        }
                        end end2 : OfficialCSRM::'Data'::'01 - CubeSat System Reference Model'::'5 - Architecture'::'Facilities'::'Development Facility' {
                            doc /* Source XMI: _19_0_2_3880181_1572367108132_55514_62831
                            UML end name: (unnamed) */
                        }
                    }
                    part def 'Integration Facility' {
                        @OfficialCSRMProfile::'Architecture Structures Profile'::'Facility';
                        doc /* Source XMI: _19_0_2_3880181_1572367209602_64636_62841
                        Stereotype Facility
                        UML kind: uml:Class */
                    }
                    part def 'Test Facility' {
                        @OfficialCSRMProfile::'Architecture Structures Profile'::'Facility';
                        doc /* Source XMI: _19_0_2_3880181_1572367329899_768794_62879
                        Stereotype Facility
                        UML kind: uml:Class */
                        part 'thermal Vacuum Chamber' : OfficialCSRM::'Data'::'01 - CubeSat System Reference Model'::'5 - Architecture'::'Facilities'::'Thermal Vacuum Chamber' {
                            doc /* Source XMI: _19_0_2_3880181_1572369324885_802131_63333
                            Stereotype PartProperty
                            UML aggregation: composite
                            UML association: _19_0_2_3880181_1572369324885_373372_63332 */
                        }
                        part 'helmoltz Cage' : OfficialCSRM::'Data'::'01 - CubeSat System Reference Model'::'5 - Architecture'::'Facilities'::'Helmoltz Cage' {
                            doc /* Source XMI: _19_0_2_3880181_1572369360182_480315_63349
                            Stereotype PartProperty
                            UML aggregation: composite
                            UML association: _19_0_2_3880181_1572369360182_259316_63348 */
                        }
                    }
                    part def 'Thermal Vacuum Chamber' {
                        @OfficialCSRMProfile::'Architecture Structures Profile'::'Equipment';
                        doc /* Source XMI: _19_0_2_3880181_1572367464070_225299_62917
                        Stereotype Equipment
                        UML kind: uml:Class */
                    }
                    part def 'Clean Room' {
                        @OfficialCSRMProfile::'Architecture Structures Profile'::'Facility';
                        doc /* Source XMI: _19_0_2_3880181_1572367563868_248933_62955
                        Stereotype Facility
                        UML kind: uml:Class */
                    }
                    connection def association_11 {
                        doc /* Source XMI: _19_0_2_3880181_1572367594212_876766_62997
                        UML end details are in the source map (SysML v2 connector ends have fixed [1..1] multiplicity). */
                        end end1 : OfficialCSRM::'Data'::'01 - CubeSat System Reference Model'::'5 - Architecture'::'Facilities'::'Production Facility' {
                            doc /* Source XMI: _19_0_2_3880181_1572367594212_695440_62998
                            Stereotype PartProperty
                            UML end name: production Facility */
                        }
                        end end2 : OfficialCSRM::'Data'::'01 - CubeSat System Reference Model'::'5 - Architecture'::'Facilities'::'Development Facility' {
                            doc /* Source XMI: _19_0_2_3880181_1572367594212_245025_62999
                            UML end name: (unnamed) */
                        }
                    }
                    connection def association_12 {
                        doc /* Source XMI: _19_0_2_3880181_1572367605436_283853_63013
                        UML end details are in the source map (SysML v2 connector ends have fixed [1..1] multiplicity). */
                        end end1 : OfficialCSRM::'Data'::'01 - CubeSat System Reference Model'::'5 - Architecture'::'Facilities'::'Clean Room' {
                            doc /* Source XMI: _19_0_2_3880181_1572367605436_425348_63014
                            Stereotype PartProperty
                            UML end name: clean Room */
                        }
                        end end2 : OfficialCSRM::'Data'::'01 - CubeSat System Reference Model'::'5 - Architecture'::'Facilities'::'Production Facility' {
                            doc /* Source XMI: _19_0_2_3880181_1572367605436_117319_63015
                            UML end name: (unnamed) */
                        }
                    }
                    part def 'Offices' {
                        @OfficialCSRMProfile::'Architecture Structures Profile'::'Facility';
                        doc /* Source XMI: _19_0_2_3880181_1572368013883_850830_63183
                        Stereotype Facility
                        UML kind: uml:Class */
                    }
                    connection def association_14 {
                        doc /* Source XMI: _19_0_2_3880181_1572368049259_579600_63225
                        UML end details are in the source map (SysML v2 connector ends have fixed [1..1] multiplicity). */
                        end end1 : OfficialCSRM::'Data'::'01 - CubeSat System Reference Model'::'5 - Architecture'::'Facilities'::'Offices' {
                            doc /* Source XMI: _19_0_2_3880181_1572368049259_232277_63226
                            Stereotype PartProperty
                            UML end name: offices */
                        }
                        end end2 : OfficialCSRM::'Data'::'01 - CubeSat System Reference Model'::'5 - Architecture'::'Facilities'::'Design Facility' {
                            doc /* Source XMI: _19_0_2_3880181_1572368049259_694900_63227
                            UML end name: (unnamed) */
                        }
                    }
                    part def 'Helmoltz Cage' {
                        @OfficialCSRMProfile::'Architecture Structures Profile'::'Equipment';
                        doc /* Source XMI: _19_0_2_3880181_1572368763384_815328_63239
                        Stereotype Equipment
                        UML kind: uml:Class */
                    }
                    connection def association_16 {
                        doc /* Source XMI: _19_0_2_3880181_1572369275230_602679_63282
                        UML end details are in the source map (SysML v2 connector ends have fixed [1..1] multiplicity). */
                        end end1 : OfficialCSRM::'Data'::'01 - CubeSat System Reference Model'::'5 - Architecture'::'Facilities'::'Integration Facility' {
                            doc /* Source XMI: _19_0_2_3880181_1572369275230_579235_63283
                            Stereotype PartProperty
                            UML end name: integration Facility */
                        }
                        end end2 : OfficialCSRM::'Data'::'01 - CubeSat System Reference Model'::'5 - Architecture'::'Facilities'::'Development Facility' {
                            doc /* Source XMI: _19_0_2_3880181_1572369275230_337177_63284
                            UML end name: (unnamed) */
                        }
                    }
                    connection def association_17 {
                        doc /* Source XMI: _19_0_2_3880181_1572369324885_373372_63332
                        UML end details are in the source map (SysML v2 connector ends have fixed [1..1] multiplicity). */
                        end end1 : OfficialCSRM::'Data'::'01 - CubeSat System Reference Model'::'5 - Architecture'::'Facilities'::'Thermal Vacuum Chamber' {
                            doc /* Source XMI: _19_0_2_3880181_1572369324885_802131_63333
                            Stereotype PartProperty
                            UML end name: thermal Vacuum Chamber */
                        }
                        end end2 : OfficialCSRM::'Data'::'01 - CubeSat System Reference Model'::'5 - Architecture'::'Facilities'::'Test Facility' {
                            doc /* Source XMI: _19_0_2_3880181_1572369324885_180643_63334
                            UML end name: (unnamed) */
                        }
                    }
                    connection def association_18 {
                        doc /* Source XMI: _19_0_2_3880181_1572369360182_259316_63348
                        UML end details are in the source map (SysML v2 connector ends have fixed [1..1] multiplicity). */
                        end end1 : OfficialCSRM::'Data'::'01 - CubeSat System Reference Model'::'5 - Architecture'::'Facilities'::'Helmoltz Cage' {
                            doc /* Source XMI: _19_0_2_3880181_1572369360182_480315_63349
                            Stereotype PartProperty
                            UML end name: helmoltz Cage */
                        }
                        end end2 : OfficialCSRM::'Data'::'01 - CubeSat System Reference Model'::'5 - Architecture'::'Facilities'::'Test Facility' {
                            doc /* Source XMI: _19_0_2_3880181_1572369360182_337625_63350
                            UML end name: (unnamed) */
                        }
                    }
                    connection def association_19 {
                        doc /* Source XMI: _19_0_2_3880181_1572378692581_144207_63171
                        UML end details are in the source map (SysML v2 connector ends have fixed [1..1] multiplicity). */
                        end end1 : OfficialCSRM::'Data'::'01 - CubeSat System Reference Model'::'5 - Architecture'::'Facilities'::'Test Facility' {
                            doc /* Source XMI: _19_0_2_3880181_1572378692581_314229_63172
                            Stereotype PartProperty
                            UML end name: test Facility */
                        }
                        end end2 : OfficialCSRM::'Data'::'01 - CubeSat System Reference Model'::'5 - Architecture'::'Facilities'::'Development Facility' {
                            doc /* Source XMI: _19_0_2_3880181_1572378692581_676435_63173
                            UML end name: (unnamed) */
                        }
                    }
                }
            }
            package '4 - Requirements' {
                doc /* Source XMI: _18_0_6_3e4019a_1472151507106_525939_12342
                Comment _19_0_2_3880181_1600785908876_82097_62844
                The Rqts and logical architecture hierarchies are parallel constructs.
                Requirement packages are numbered to be consistent with the corresponding architecture packages.
                Individual Rqts are numbered uniquely according to a prefix based on the name of the Rqts packages.  The modeler can easily change the prefix.
                The CSRM provides for tracing Rqts from stakeholders, behaviors, and technical measures down to subsystems and components and then to validation and verification activities.
                The requirement element properties include:
                Rationale    Traced To     Traced From    Derived From    Refined By    Verify Method    Verified By    Satisfied By
                Comment _19_0_3_2b0010b_1619536885345_618868_22192 (Explanation)
                The modeler can easily change the prefix by Select a requirement in the containment tree and Select Element Numbering
                Comment _19_0_3_2b0010b_1619536885356_427495_22203 (HowTo)
                Double-click on table and add and delete requirements as needed
                Click on Add New to add a new requirement to the containment tree and to the table.
                Right click the new requirement in the table then left click Select in Containment Tree to navigate to the new element.
                Select an requirement and click on Delete to delete from the requirement table and the Containment Tree.
                Comment _19_0_3_2b0010b_1619536885363_89589_22214 (HowTo)
                Double-click on the CubeSat, Ground Segment, CubeSat Subsystem, and Ground Subsystem requirement packages to navigate to the requirement tables.
                Comment _19_0_3_2b0010b_1619536885368_134395_22225 (Explanation)
                The requirement element properties include:
                Rationale    Traced To     Traced From    Derived From    Verify Method    Verified By    Satisfied By
                Comment _19_0_3_2b0010b_1619536885372_64195_22236 (Explanation)
                Requirement packages are numbered to be consistent with the corresponding architecture packages.
                Individual requirements are numbered uniquely according to a prefix based on the name of the requirements packages.
                Comment _19_0_3_2b0010b_1619536885375_539114_22247 (Explanation)
                The requirement elements reside in the containment tree.  The requirement tables are views of the requirement elements.  A table can be deleted but the requirement elements and their hierarchy remains.
                Requirements are added to the table using “Add New or “Add Nested” and the requirement Ids are automatically updated.
                Comment _19_0_2_3880181_1637272763825_199768_56156 (Explanation)
                Requirements Hierarchy - Population
                UML kind: uml:Package */
                package 'L2 Segment Rqts' {
                    doc /* Source XMI: _18_0_6_3e4019a_1472151552166_275_13482
                    Comment _19_0_2_3880181_1600870972528_242967_63373
                    The package for Segment Rqts.  To be populated by a mission-specific team.
                    UML kind: uml:Package */
                    package 'L2.1 Space Segment Rqts' {
                        doc /* Source XMI: _18_0_6_3e4019a_1472151509109_25753_12449
                        Comment _19_0_2_3880181_1600870884915_591502_63372
                        Package for Space Segment Rqts
                        UML kind: uml:Package */
                        package 'L2.1.1 CubeSat Rqts' {
                            doc /* Source XMI: _18_4_1_3880181_1492798620746_277829_45509
                            Comment _19_0_2_3880181_1600870660941_850869_63371
                            Repository for CubeSat Rqts.  To be populated by a mission-specific team.
                            Comment _19_0_3_2b0010b_1619212386381_66067_7154 (HowTo)
                            Double-click on the requirements table and then click on Add New to add a new requirement to the containment tree and to the table.
                            Right click the new element in the table then left click Select in Containment Tree to navigate to the new element.
                            The table can also be used to modify and delete requirements.
                            Comment _19_0_2_3880181_1637273057636_656610_56199 (Explanation)
                            CubeSat Rqts - Population
                            UML kind: uml:Package */
                            requirement def 'CubeSat Rqts Group' {
                                @OfficialCSRMProfile::'Concerns and Requirements Profile'::'CubeSatRequirement';
                                doc /* The Group provides the prefix and numbering scheme - which is easy to change. */
                                comment /* Source XMI: _18_5_1_3880181_1500212911572_169729_56262
                                Stereotype CubeSatRequirement: Text=The Group provides the prefix and numbering scheme - which is easy to change., Id=CSat_1
                                UML kind: uml:Class */
                                requirement def 'Requirement Name' {
                                    @OfficialCSRMProfile::'Concerns and Requirements Profile'::'CubeSatRequirement';
                                    doc /* Shall Statement */
                                    comment /* Source XMI: _19_0_2_3880181_1572554869340_101975_63223
                                    Stereotype CubeSatRequirement: Text=Shall Statement, Id=CSat_1.1
                                    UML kind: uml:Class */
                                }
                            }
                        }
                    }
                    package 'L2.2 Ground Segment Rqts' {
                        doc /* Source XMI: _18_0_6_3e4019a_1472151509123_152831_12467
                        Comment _19_0_2_3880181_1600870617146_337069_63370
                        Repository for ground segment Rqts.
                        Comment _19_0_3_2b0010b_1619212410664_543031_7210 (HowTo)
                        Double-click on the requirements table and then click on Add New to add a new requirement to the containment tree and to the table.
                        Right click the new element in the table then left click Select in Containment Tree to navigate to the new element.
                        The table can also be used to modify and delete requirements.
                        Comment _19_0_2_3880181_1637274366605_467824_56514 (Explanation)
                        Ground Segment Rqts - Population
                        UML kind: uml:Package */
                        part def 'Ground Segment Rqts Group' {
                            @OfficialCSRMProfile::'Concerns and Requirements Profile'::'Group';
                            doc /* Source XMI: _18_5_1_3880181_1500213247675_786231_56336
                            Stereotype Group: Text=The Group provides the prefix and numbering scheme - which is easy to change., Id=GSeg_1
                            UML kind: uml:Class */
                            requirement def 'Ground Segment Requirement A' {
                                @OfficialCSRMProfile::'Concerns and Requirements Profile'::'GroundSegmentRequirement';
                                doc /* Shall statement */
                                comment /* Source XMI: _19_0_2_3880181_1570637710189_138346_63400
                                Stereotype GroundSegmentRequirement: Text=Shall statement, Id=GSeg_1.2
                                UML kind: uml:Class */
                            }
                        }
                    }
                }
                package 'L4 Component Rqts' {
                    doc /* Source XMI: _18_4_1_3880181_1492800941685_607070_45711
                    Comment _19_0_2_3880181_1600880533677_616896_62941
                    Package for CubeSat and Ground subsystems components Rqts.  To be populated by a mission-specific team.
                    UML kind: uml:Package */
                    package 'L4.1 CubeSat Subsystems Components Rqts' {
                        doc /* Source XMI: _18_4_1_3880181_1492800653453_310132_45710
                        Comment _19_0_2_3880181_1600880701034_644512_62942
                        The package is for CubeSat subsystem components Rqts.  To be populated by a mission-specific team.
                        Comment _19_0_3_2b0010b_1619533213332_333021_14318 (HowTo)
                        Double-click on a requirements table and then click on Add New to add a new requirement to the containment tree and to the table.
                        Right click the new element in the table then left click Select in Containment Tree to navigate to the new element.
                        The table can also be used to modify and delete requirements.
                        Comment _19_0_2_3880181_1637273899549_512161_56471 (Explanation)
                        CubeSat Components Rqts - Population
                        UML kind: uml:Package */
                        package 'L4.1.1 Mission Payload Component Rqts' {
                            doc /* Source XMI: _18_4_1_3880181_1492801269618_268223_45720
                            Comment _19_0_2_3880181_1600881674942_687463_63119
                            The repository for Mission Payload components Rqts.  To be populated by a mission-specific team.
                            UML kind: uml:Package */
                            part def 'Mission Payload Component Rqts Breaker' {
                                @OfficialCSRMProfile::'Concerns and Requirements Profile'::'Group';
                                doc /* Source XMI: _18_5_1_3880181_1500235047390_873223_57199
                                Stereotype Group: Text=The breaker provides the prefix and number scheme., Id=MpCmp_1
                                UML kind: uml:Class */
                                requirement def 'Requirement Name' {
                                    @OfficialCSRMProfile::'Concerns and Requirements Profile'::'ComponentRequirement';
                                    doc /* Shall statement */
                                    comment /* Source XMI: _19_0_2_3880181_1561561106417_620702_61542
                                    Stereotype ComponentRequirement: Text=Shall statement, Id=MpCmp_1.1
                                    UML kind: uml:Class */
                                }
                            }
                        }
                        package 'L4.1.2 Command and Data Handling Component Rqts' {
                            doc /* Source XMI: _18_4_1_3880181_1492801159647_219972_45712
                            Comment _19_0_2_3880181_1600881810666_809623_63120
                            The repository for Command and Data Handling components requirement.  To be populated by a mission-specific team.
                            UML kind: uml:Package */
                            part def 'Command and Data Handling Component Rqts Breaker' {
                                @OfficialCSRMProfile::'Concerns and Requirements Profile'::'Group';
                                doc /* Source XMI: _18_5_1_3880181_1500235367369_639718_57259
                                Stereotype Group: Text=The breaker provides the prefix and number scheme., Id=CdCmp__1
                                UML kind: uml:Class */
                                requirement def 'Requirement Name' {
                                    @OfficialCSRMProfile::'Concerns and Requirements Profile'::'ComponentRequirement';
                                    doc /* Shall statement */
                                    comment /* Source XMI: _19_0_2_3880181_1561561293636_473787_61594
                                    Stereotype ComponentRequirement: Text=Shall statement, Id=CdCmp__1.1
                                    UML kind: uml:Class */
                                }
                            }
                        }
                        package 'L4.1.3 Communication Component Rqts' {
                            doc /* Source XMI: _18_4_1_3880181_1492801159647_33118_45713
                            Comment _19_0_2_3880181_1600881875341_544098_63121
                            The repository for Communication components Rqts.  To be populated by a mission-specific team.
                            UML kind: uml:Package */
                            part def 'Communication Component Rqts Breaker' {
                                @OfficialCSRMProfile::'Concerns and Requirements Profile'::'Group';
                                doc /* Source XMI: _18_5_1_3880181_1500235603612_857920_57297
                                Stereotype Group: Text=The breaker provides the prefix and number scheme., Id=CmCmp_1
                                UML kind: uml:Class */
                                requirement def 'Requirement Name' {
                                    @OfficialCSRMProfile::'Concerns and Requirements Profile'::'ComponentRequirement';
                                    doc /* Shall statement */
                                    comment /* Source XMI: _19_0_2_3880181_1561561992717_631137_61295
                                    Stereotype ComponentRequirement: Text=Shall statement, Id=CmCmp_1.1
                                    UML kind: uml:Class */
                                }
                            }
                        }
                        package 'L4.1.4 Attitude Determination and Control Component Rqts' {
                            doc /* Source XMI: _18_4_1_3880181_1492801159647_158957_45714
                            Comment _19_0_2_3880181_1600881942450_592818_63122
                            The repository for Attitude Determination and Control components Rqts.  To be populated by a mission-specific team.
                            UML kind: uml:Package */
                            part def 'Attitude Determination and Control Component Rqts Breaker' {
                                @OfficialCSRMProfile::'Concerns and Requirements Profile'::'Group';
                                doc /* Source XMI: _18_5_1_3880181_1500235806575_496735_57348
                                Stereotype Group: Text=The breaker Group the prefix and number scheme., Id=AdCmp_1
                                UML kind: uml:Class */
                                requirement def 'Requirement Name' {
                                    @OfficialCSRMProfile::'Concerns and Requirements Profile'::'ComponentRequirement';
                                    doc /* Shall statement */
                                    comment /* Source XMI: _19_0_2_3880181_1561562047744_111084_61326
                                    Stereotype ComponentRequirement: Text=Shall statement, Id=AdCmp_1.1
                                    UML kind: uml:Class */
                                }
                            }
                        }
                        package 'L4.1.5 Guidance Navigation and Control Component Rqts' {
                            doc /* Source XMI: _18_4_1_3880181_1492801159647_291816_45715
                            Comment _19_0_2_3880181_1600882029179_908521_63142
                            The repository for Guidance Navigation and Control components Rqts.  To be populated by a mission-specific team.
                            UML kind: uml:Package */
                            part def 'Guidance Navigation and Control Component Rqts Group' {
                                @OfficialCSRMProfile::'Concerns and Requirements Profile'::'Group';
                                doc /* Source XMI: _18_5_1_3880181_1500235989182_278465_57398
                                Stereotype Group: Text=The group
                                 provides the prefix and number scheme., Id=GnCmp_1
                                UML kind: uml:Class */
                                requirement def 'Requirement Name' {
                                    @OfficialCSRMProfile::'Concerns and Requirements Profile'::'ComponentRequirement';
                                    doc /* Shall statement */
                                    comment /* Source XMI: _19_0_2_3880181_1561562150272_840440_61357
                                    Stereotype ComponentRequirement: Text=Shall statement, Id=GnCmp_1.1
                                    UML kind: uml:Class */
                                }
                            }
                        }
                        package 'L4.1.6 Structures and Mechanisms Component Rqts' {
                            doc /* Source XMI: _18_4_1_3880181_1492801159647_576575_45716
                            Comment _19_0_2_3880181_1600882092786_528035_63143
                            The repository for Structures and Mechanisms components Rqts.  To be populated by a mission-specific team.
                            UML kind: uml:Package */
                            part def 'Structures and Mechanisms Component Rqts Group' {
                                @OfficialCSRMProfile::'Concerns and Requirements Profile'::'Group';
                                doc /* Source XMI: _18_5_1_3880181_1500236131544_752150_57448
                                Stereotype Group: Text=The breaker provides the prefix and number scheme., Id=SmCmp_1
                                UML kind: uml:Class */
                                requirement def 'Requirement Name' {
                                    @OfficialCSRMProfile::'Concerns and Requirements Profile'::'ComponentRequirement';
                                    doc /* Shall statement */
                                    comment /* Source XMI: _19_0_2_3880181_1561562387169_689623_61434
                                    Stereotype ComponentRequirement: Text=Shall statement, Id=SmCmp_1.1
                                    UML kind: uml:Class */
                                }
                            }
                        }
                        package 'L4.1.7 Power Component Rqts' {
                            doc /* Source XMI: _18_4_1_3880181_1492801159647_917026_45717
                            Comment _19_0_2_3880181_1600882159239_880611_63144
                            Repository for Power components Rqts.  To be populated by a mission-specific team.
                            UML kind: uml:Package */
                            part def 'Power Component Rqts Breaker' {
                                @OfficialCSRMProfile::'Concerns and Requirements Profile'::'Group';
                                doc /* Source XMI: _18_5_1_3880181_1500236346164_18226_57514
                                Stereotype Group: Text=The breaker provides the prefix and number scheme., Id=PoCmp_1
                                UML kind: uml:Class */
                                requirement def 'Requirement Name' {
                                    @OfficialCSRMProfile::'Concerns and Requirements Profile'::'ComponentRequirement';
                                    doc /* Shall statement */
                                    comment /* Source XMI: _19_0_2_3880181_1561562481711_288462_61613
                                    Stereotype ComponentRequirement: Text=Shall statement, Id=PoCmp_1.1
                                    UML kind: uml:Class */
                                }
                            }
                        }
                        package 'L4.1.8 Thermal Component Rqts' {
                            doc /* Source XMI: _18_4_1_3880181_1492801159663_165065_45718
                            Comment _19_0_2_3880181_1600882206929_823304_63145
                            Repository for Thermal components Rqts.  To be populated by a mission-specific team.
                            UML kind: uml:Package */
                            part def 'Thermal Component Rqts Group' {
                                @OfficialCSRMProfile::'Concerns and Requirements Profile'::'Group';
                                doc /* Source XMI: _18_5_1_3880181_1500236518821_136919_57564
                                Stereotype Group: Text=The breaker provides the prefix and number scheme., Id=ThCmp_1
                                UML kind: uml:Class */
                                requirement def 'Requirement Name' {
                                    @OfficialCSRMProfile::'Concerns and Requirements Profile'::'ComponentRequirement';
                                    doc /* Shall statement */
                                    comment /* Source XMI: _19_0_2_3880181_1561562610321_620636_61657
                                    Stereotype ComponentRequirement: Text=Shall statement, Id=ThCmp_1.1
                                    UML kind: uml:Class */
                                }
                            }
                        }
                        package 'L4.1.9 Propulsion Component Rqts' {
                            doc /* Source XMI: _18_4_1_3880181_1492801159663_788044_45719
                            Comment _19_0_2_3880181_1600882266558_819379_63146
                            The repository for Propulsion components Rqts.  To be populated by a mission-specific team.
                            UML kind: uml:Package */
                            part def 'Propulsion Component Rqts Group' {
                                @OfficialCSRMProfile::'Concerns and Requirements Profile'::'Group';
                                doc /* Source XMI: _18_5_1_3880181_1500236840091_286462_57614
                                Stereotype Group: Text=The breaker provides the prefix and number scheme., Id=PrCmp_1
                                UML kind: uml:Class */
                                requirement def 'Requirement Name' {
                                    @OfficialCSRMProfile::'Concerns and Requirements Profile'::'ComponentRequirement';
                                    doc /* Shall statement */
                                    comment /* Source XMI: _19_0_2_3880181_1561562725413_678276_61703
                                    Stereotype ComponentRequirement: Text=Shall statement, Id=PrCmp_1.1
                                    UML kind: uml:Class */
                                }
                            }
                        }
                    }
                    package 'L4.2 Ground Subsystems Components Rqts' {
                        doc /* Source XMI: _18_4_1_3880181_1493420237968_847957_47153
                        Comment _19_0_2_3880181_1600881460051_988390_63099
                        This package is for the Ground subsystems components Rqts.  To be populated by a mission-specific team.
                        Comment _19_0_3_2b0010b_1619534903147_958402_15259 (HowTo)
                        Double-click on a requirements table and then click on Add New to add a new requirement to the containment tree and to the table.
                        Right click the new element in the table then left click Select in Containment Tree to navigate to the new element.
                        The table can also be used to modify and delete requirements.
                        Comment _19_0_2_3880181_1637274889497_432765_56733
                        Comment _19_0_2_3880181_1637275159326_307473_56746 (Explanation)
                        Ground Components Rqts - Population
                        UML kind: uml:Package */
                        package 'L4.2.1 Plan and Schedule Component Rqts' {
                            doc /* Source XMI: _18_4_1_3880181_1494257648901_680589_52034
                            Comment _19_0_2_3880181_1600882416925_36938_63147
                            Repository for Plan and Schedule components Rqts.  To be populated by a mission-specific team.
                            UML kind: uml:Package */
                            part def 'Plan and Schedule Component Rqts Group' {
                                @OfficialCSRMProfile::'Concerns and Requirements Profile'::'Group';
                                doc /* Source XMI: _18_5_1_3880181_1500237798808_813542_56498
                                Stereotype Group: Text=The Group provides the prefix and number scheme., Id=PsCmp_1
                                UML kind: uml:Class */
                                requirement def 'Requirement Name' {
                                    @OfficialCSRMProfile::'Concerns and Requirements Profile'::'ComponentRequirement';
                                    doc /* Shall statement */
                                    comment /* Source XMI: _19_0_2_3880181_1561571855404_455614_61374
                                    Stereotype ComponentRequirement: Text=Shall statement, Id=PsCmp_1.1
                                    UML kind: uml:Class */
                                }
                            }
                        }
                        package 'L4.2.2 Spacecraft Command Component Rqts' {
                            doc /* Source XMI: _18_4_1_3880181_1494257733176_453207_52035
                            Comment _19_0_2_3880181_1600882482593_34214_63148
                            Repository for Spacecraft Command compoents Rqts.  To be populated by a mission-specific team.
                            UML kind: uml:Package */
                            part def 'Spacecraft Command Component Rqts Breaker' {
                                @OfficialCSRMProfile::'Concerns and Requirements Profile'::'Group';
                                doc /* Source XMI: _18_5_1_3880181_1500237980744_957946_56561
                                Stereotype Group: Text=The breaker provides the prefix and number scheme., Id=ScCmp_1
                                UML kind: uml:Class */
                                requirement def 'Requirement Name' {
                                    @OfficialCSRMProfile::'Concerns and Requirements Profile'::'ComponentRequirement';
                                    doc /* Shall statement */
                                    comment /* Source XMI: _19_0_2_3880181_1561571910481_828009_61405
                                    Stereotype ComponentRequirement: Text=Shall statement, Id=ScCmp_1.1
                                    UML kind: uml:Class */
                                }
                            }
                        }
                        package 'L4.2.3 Ground Equipment Control Component Rqts' {
                            doc /* Source XMI: _18_4_1_3880181_1494257815155_458712_52036
                            Comment _19_0_2_3880181_1600882555643_292343_63149
                            A repository for Gound Equipment Control components.  To be populated by a mission-specific team.
                            UML kind: uml:Package */
                            part def 'Ground Equipment Control Component Rqts Breaker' {
                                @OfficialCSRMProfile::'Concerns and Requirements Profile'::'Group';
                                doc /* Source XMI: _18_5_1_3880181_1500238215117_854255_56612
                                Stereotype Group: Text=The breaker provides the prefix and number scheme., Id=GeCmp_1
                                UML kind: uml:Class */
                                requirement def 'Requirement Name' {
                                    @OfficialCSRMProfile::'Concerns and Requirements Profile'::'ComponentRequirement';
                                    doc /* Shall statement */
                                    comment /* Source XMI: _19_0_2_3880181_1561572024177_763941_61447
                                    Stereotype ComponentRequirement: Text=Shall statement, Id=GeCmp_1.1
                                    UML kind: uml:Class */
                                }
                            }
                        }
                        package 'L4.2.4 Space-Ground Communication Component Rqts' {
                            doc /* Source XMI: _18_4_1_3880181_1494257903037_703349_52037
                            Comment _19_0_2_3880181_1600882621648_795081_63150
                            A repository for Space-Ground Communication components Rqts.  To be populated by a mission-specific team.
                            UML kind: uml:Package */
                            part def 'Space-Ground Communication Component Rqts Breaker' {
                                @OfficialCSRMProfile::'Concerns and Requirements Profile'::'Group';
                                doc /* Source XMI: _18_5_1_3880181_1500238412894_543030_56676
                                Stereotype Group: Text=The breaker provides the prefix and number scheme., Id=SgCmp_1
                                UML kind: uml:Class */
                                requirement def 'Requirement Name' {
                                    @OfficialCSRMProfile::'Concerns and Requirements Profile'::'ComponentRequirement';
                                    doc /* Shall statement */
                                    comment /* Source XMI: _19_0_2_3880181_1561572072594_763554_61478
                                    Stereotype ComponentRequirement: Text=Shall statement, Id=SgCmp_1.1
                                    UML kind: uml:Class */
                                }
                            }
                        }
                        package 'L4.2.5 Mission Data Processing Component Rqts' {
                            doc /* Source XMI: _18_4_1_3880181_1494257975380_28913_52038
                            Comment _19_0_2_3880181_1600882680317_309248_63151
                            A repository for Mission Data Processing components Rqts.  To be populated by a mission-specific team.
                            UML kind: uml:Package */
                            part def 'Mission Data Processing Components Rqts Breaker' {
                                @OfficialCSRMProfile::'Concerns and Requirements Profile'::'Group';
                                doc /* Source XMI: _18_5_1_3880181_1500238638096_583162_56715
                                Stereotype Group: Text=The breaker provides the prefix and number scheme., Id=DpCmp_1
                                UML kind: uml:Class */
                                requirement def 'Requirement Name' {
                                    @OfficialCSRMProfile::'Concerns and Requirements Profile'::'ComponentRequirement';
                                    doc /* Shall statement */
                                    comment /* Source XMI: _19_0_2_3880181_1561572128881_343088_61509
                                    Stereotype ComponentRequirement: Text=Shall statement, Id=DpCmp_1.1
                                    UML kind: uml:Class */
                                }
                            }
                        }
                        package 'L4.2.6 Mission Data Dissemination Component Rqts' {
                            doc /* Source XMI: _18_4_1_3880181_1494258029222_415004_52039
                            Comment _19_0_2_3880181_1600882774927_361996_63152
                            A repository for Mission Data Dissemination components Rqts.  To be populated by a mission-specific team.
                            UML kind: uml:Package */
                            part def 'Mission Data Dissemination Component Rqts Group' {
                                @OfficialCSRMProfile::'Concerns and Requirements Profile'::'Group';
                                doc /* Source XMI: _18_5_1_3880181_1500238787060_451798_56765
                                Stereotype Group: Text=The breaker provides the prefix and number scheme., Id=DdCmp_1
                                UML kind: uml:Class */
                                requirement def 'Requirement Name' {
                                    @OfficialCSRMProfile::'Concerns and Requirements Profile'::'ComponentRequirement';
                                    doc /* Shall statement */
                                    comment /* Source XMI: _19_0_2_3880181_1561572612699_137206_61798
                                    Stereotype ComponentRequirement: Text=Shall statement, Id=DdCmp_1.1
                                    UML kind: uml:Class */
                                }
                            }
                        }
                        package 'L4.2.7 Network Component Rqts' {
                            doc /* Source XMI: _18_4_1_3880181_1494258120914_582030_52040
                            Comment _19_0_2_3880181_1600882851247_881651_63153
                            A repository for Network components Rqts.  To be populated by a mission-specific team.
                            UML kind: uml:Package */
                        }
                        package 'L4.2.8 Facility Component Rqts' {
                            doc /* Source XMI: _18_4_1_3880181_1494258193716_913314_52041
                            Comment _19_0_2_3880181_1600882891398_319185_63154
                            A repository for Facility components Rqts.  To be populated by a mission-specific team.
                            UML kind: uml:Package */
                            part def 'Facility Component Rqts Group' {
                                @OfficialCSRMProfile::'Concerns and Requirements Profile'::'Group';
                                doc /* Source XMI: _18_5_1_3880181_1500239244157_224241_56949
                                Stereotype Group: Text=The breaker provides the prefix and number scheme., Id=FaCmp_1
                                UML kind: uml:Class */
                                requirement def 'Requirement Name' {
                                    @OfficialCSRMProfile::'Concerns and Requirements Profile'::'ComponentRequirement';
                                    doc /* Shall statement */
                                    comment /* Source XMI: _19_0_2_3880181_1561572388131_937106_61612
                                    Stereotype ComponentRequirement: Text=Shall statement, Id=FaCmp_1.1
                                    UML kind: uml:Class */
                                }
                            }
                        }
                    }
                }
                package 'L3 Subsystem Rqts' {
                    doc /* Source XMI: _18_0_6_3e4019a_1472151552167_784594_13484
                    Comment _19_0_2_3880181_1600871229674_789375_63375
                    The package for Subsystem Rqts.  To be populated by a mission-specific team.
                    UML kind: uml:Package */
                    package 'L3.2 Ground Subsystems Rqts' {
                        doc /* Source XMI: _18_0_6_3e4019a_1472151563829_192578_14079
                        Comment _19_0_2_3880181_1600871490399_521124_63377
                        Repository for Ground Subsystem Rqts.  To be populated by a mission-specific team.
                        Comment _19_0_3_2b0010b_1619213035328_715786_7903 (HowTo)
                        Double-click on the requirements table and then click on Add New to add a new requirement to the containment tree and to the table.
                        Right click the new element in the table then left click Select in Containment Tree to navigate to the new element.
                        The table can also be used to modify and delete requirements.
                        Comment _19_0_2_3880181_1637274622091_755858_56627 (Explanation)
                        Ground Subsystems Rqts - Population
                        UML kind: uml:Package */
                        package 'L3.2.1 Plan and Schedule Subsystem Rqts' {
                            doc /* Source XMI: _18_4_1_3880181_1494258700110_367674_52074
                            Comment _19_0_2_3880181_1600879651487_632177_62904
                            The repository for Plan and Schedule subsystem Rqts.  To be populated by a mission-specific team.
                            UML kind: uml:Package */
                            part def 'Plan and Schedule Subsystem Rqts Group' {
                                @OfficialCSRMProfile::'Concerns and Requirements Profile'::'Group';
                                doc /* Source XMI: _18_5_1_3880181_1500231579349_909663_56579
                                Stereotype Group: Text=The Group provides the prefix and numbering scheme - which is easy to change., Id=PsSub_1
                                UML kind: uml:Class */
                                requirement def 'Plan and Schedule Requirement A' {
                                    @OfficialCSRMProfile::'Concerns and Requirements Profile'::'SubsystemRequirement';
                                    doc /* Shall statement */
                                    comment /* Source XMI: _19_0_2_3880181_1561494456715_744905_61785
                                    Stereotype SubsystemRequirement: Text=Shall statement, Id=PsSub_1.1
                                    Comment _19_0_3_2b0010b_1613336733487_864350_12742 (Rationale)
                                    The rationale model element can be associated with a requirement, a requirement relationship, or any other model element. It is intended to capture the reason for a particular decision. It is based on the comment element.
                                    UML kind: uml:Class */
                                }
                            }
                        }
                        package 'L3.2.2 Spacecraft Command Subsystem Rqts' {
                            doc /* Source XMI: _18_4_1_3880181_1494258755937_310693_52075
                            Comment _19_0_2_3880181_1600879729142_119820_62905
                            The repository for Spacecraft Command subsystem Rqts.  To be populated by a mission-specific team.
                            UML kind: uml:Package */
                            part def 'Spacecraft Command Subsystem Rqts Group' {
                                @OfficialCSRMProfile::'Concerns and Requirements Profile'::'Group';
                                doc /* Source XMI: _18_5_1_3880181_1500231751178_724172_56612
                                Stereotype Group: Text=The Group provides the prefix and numbering scheme - which is easy to change., Id=ScSub_1
                                UML kind: uml:Class */
                                requirement def 'Requirement Name' {
                                    @OfficialCSRMProfile::'Concerns and Requirements Profile'::'SubsystemRequirement';
                                    doc /* Shall statement */
                                    comment /* Source XMI: _19_0_2_3880181_1561494521828_263706_61816
                                    Stereotype SubsystemRequirement: Text=Shall statement, Id=ScSub_1.1
                                    UML kind: uml:Class */
                                }
                            }
                        }
                        package 'L3.2.3 Ground Equipment Control Subsystem Rqts' {
                            doc /* Source XMI: _18_4_1_3880181_1494258869935_221832_52076
                            Comment _19_0_2_3880181_1600879808030_589817_62906
                            The repository for Ground Equipment Control subsystem Rqts.  To be populated by a mission-specific team.
                            UML kind: uml:Package */
                            part def 'Ground Equipment Control Subsystem Rqts Group' {
                                @OfficialCSRMProfile::'Concerns and Requirements Profile'::'Group';
                                doc /* Source XMI: _18_5_1_3880181_1500232515212_222584_56691
                                Stereotype Group: Text=The Group provides the prefix and numbering scheme - which is easy to change., Id=GeSub_1
                                UML kind: uml:Class */
                                requirement def 'Requirement Name' {
                                    @OfficialCSRMProfile::'Concerns and Requirements Profile'::'SubsystemRequirement';
                                    doc /* Shall statement */
                                    comment /* Source XMI: _19_0_2_3880181_1561494582693_118484_61846
                                    Stereotype SubsystemRequirement: Text=Shall statement, Id=GeSub_1.1
                                    UML kind: uml:Class */
                                }
                            }
                        }
                        package 'L3.2.4 Space-Ground Communication Subsystem Rqts' {
                            doc /* Source XMI: _18_4_1_3880181_1494258982504_964642_52077
                            Comment _19_0_2_3880181_1600879949517_502913_62907
                            The repository for Space-Ground Communication subsystem Rqts.  To be populated by a mission-specific team.
                            UML kind: uml:Package */
                            part def 'Space-Ground Communications Subsystem Rqts Group' {
                                @OfficialCSRMProfile::'Concerns and Requirements Profile'::'Group';
                                doc /* Source XMI: _18_5_1_3880181_1500232889390_282282_56751
                                Stereotype Group: Text=The Group provides the prefix and numbering scheme - which is easy to change., Id=SgSub_1
                                UML kind: uml:Class */
                                requirement def 'Requirement Name' {
                                    @OfficialCSRMProfile::'Concerns and Requirements Profile'::'SubsystemRequirement';
                                    doc /* Shall statement */
                                    comment /* Source XMI: _19_0_2_3880181_1561494702516_875148_61878
                                    Stereotype SubsystemRequirement: Text=Shall statement, Id=SgSub_1.1
                                    UML kind: uml:Class */
                                }
                            }
                        }
                        package 'L3.2.5 Mission Data Processing Subsystem Rqts' {
                            doc /* Source XMI: _18_4_1_3880181_1494259058571_538020_52078
                            Comment _19_0_2_3880181_1600880028159_150644_62908
                            The repository for Mission Data Processing subsystem Rqts.  To be populated by a mission-specific team.
                            UML kind: uml:Package */
                            part def 'Mission Data Processing Subsystem Rqts Group' {
                                @OfficialCSRMProfile::'Concerns and Requirements Profile'::'Group';
                                doc /* Source XMI: _18_5_1_3880181_1500233109448_755777_56803
                                Stereotype Group: Text=The Group provides the prefix and numbering scheme - which is easy to change., Id=DpSub_1
                                UML kind: uml:Class */
                                requirement def 'Requirement Name' {
                                    @OfficialCSRMProfile::'Concerns and Requirements Profile'::'SubsystemRequirement';
                                    doc /* Shall statement */
                                    comment /* Source XMI: _19_0_2_3880181_1561494755817_864861_61909
                                    Stereotype SubsystemRequirement: Text=Shall statement, Id=DpSub_1.1
                                    UML kind: uml:Class */
                                }
                            }
                        }
                        package 'L3.2.6 Mission Data Dissemination Subsystem Rqts' {
                            doc /* Source XMI: _18_4_1_3880181_1494259142205_290533_52079
                            Comment _19_0_2_3880181_1600880125132_75496_62909
                            The repository for Mission Data Dissemination subsystem Rqts.  To be populated by a mission-specific team.
                            UML kind: uml:Package */
                            part def 'Mission Data Dissemination Rqts Group' {
                                @OfficialCSRMProfile::'Concerns and Requirements Profile'::'Group';
                                doc /* Source XMI: _18_5_1_3880181_1500233317472_8344_56848
                                Stereotype Group: Text=The Group provides the prefix and numbering scheme - which is easy to change., Id=DdSub_1
                                UML kind: uml:Class */
                                requirement def 'Requirement Name' {
                                    @OfficialCSRMProfile::'Concerns and Requirements Profile'::'SubsystemRequirement';
                                    doc /* Shall statement */
                                    comment /* Source XMI: _19_0_2_3880181_1561494810781_293426_61941
                                    Stereotype SubsystemRequirement: Text=Shall statement, Id=DdSub_1.1
                                    UML kind: uml:Class */
                                }
                            }
                        }
                        package 'L3.2.7 Network Subsystem Rqts' {
                            doc /* Source XMI: _18_4_1_3880181_1494259211445_131383_52080
                            Comment _19_0_2_3880181_1600880219625_410188_62929
                            The repository for Network subsystem Rqts.  To be populated by a mission-specific team.
                            UML kind: uml:Package */
                            part def 'Network Subsystem Rqts Group' {
                                @OfficialCSRMProfile::'Concerns and Requirements Profile'::'Group';
                                doc /* Source XMI: _18_5_1_3880181_1500233537871_15531_56887
                                Stereotype Group: Text=The Group provides the prefix and numbering scheme - which is easy to change., Id=NeSub_1
                                UML kind: uml:Class */
                                requirement def 'Requirement Name' {
                                    @OfficialCSRMProfile::'Concerns and Requirements Profile'::'SubsystemRequirement';
                                    doc /* Shall statement */
                                    comment /* Source XMI: _19_0_2_3880181_1561494893812_730027_61972
                                    Stereotype SubsystemRequirement: Text=Shall statement, Id=NeSub_1.1
                                    UML kind: uml:Class */
                                }
                            }
                        }
                        package 'L3.2.8 Facility Subsystem Rqts' {
                            doc /* Source XMI: _18_4_1_3880181_1494259272163_983409_52081
                            Comment _19_0_2_3880181_1600880266064_214236_62930
                            The repository for Facility subsystem Rqts.  To be populated by a mission-specific team.
                            UML kind: uml:Package */
                            part def 'Facility Subsystem Rqts Group' {
                                @OfficialCSRMProfile::'Concerns and Requirements Profile'::'Group';
                                doc /* Source XMI: _18_5_1_3880181_1500233729006_360089_56949
                                Stereotype Group: Text=The Group provides the prefix and numbering scheme - which is easy to change., Id=FaSub_1
                                UML kind: uml:Class */
                                requirement def 'Requirement Name' {
                                    @OfficialCSRMProfile::'Concerns and Requirements Profile'::'SubsystemRequirement';
                                    doc /* Shall statement */
                                    comment /* Source XMI: _19_0_2_3880181_1561495094182_349347_62007
                                    Stereotype SubsystemRequirement: Text=Shall statement, Id=FaSub_1.1
                                    UML kind: uml:Class */
                                }
                            }
                        }
                    }
                    package 'L3.1 CubeSat Subsystems Rqts' {
                        doc /* Source XMI: _18_0_6_3e4019a_1472151563829_284177_14080
                        Comment _19_0_2_3880181_1600871309263_672920_63376
                        Repository for CubeSat Subsystem Rqts.  To be populated by a mission-specific team.
                        Comment _19_0_3_2b0010b_1619212725689_609167_7740 (HowTo)
                        Double-click on the requirements table and then click on Add New to add a new requirement to the containment tree and to the table.
                        Right click the new element in the table then left click Select in Containment Tree to navigate to the new element.
                        The table can also be used to modify and delete requirements.
                        Comment _19_0_2_3880181_1637273624729_431031_56340 (Explanation)
                        CubeSat Subsystems Rqts - Popuation
                        UML kind: uml:Package */
                        package 'L3.1.1 Mission Payload Rqts' {
                            doc /* Source XMI: _18_4_1_3880181_1492798893387_476519_45635
                            Comment _19_0_2_3880181_1600871802552_739423_63397
                            The repository for Mission Payload Rqts. To be populated by a mission-specific team.
                            UML kind: uml:Package */
                            part def 'Mission Payload Rqts Group' {
                                @OfficialCSRMProfile::'Concerns and Requirements Profile'::'Group';
                                doc /* Source XMI: _18_5_1_3880181_1500215072132_903002_55096
                                Stereotype Group: Text=The Group provides the prefix and numbering scheme - which is easy to change., Id=MpSub_1
                                UML kind: uml:Class */
                                requirement def 'Requirement Name' {
                                    @OfficialCSRMProfile::'Concerns and Requirements Profile'::'SubsystemRequirement';
                                    doc /* Shall statement */
                                    comment /* Source XMI: _19_0_2_3880181_1572555030269_231001_63382
                                    Stereotype SubsystemRequirement: Text=Shall statement, Id=MpSub_1.1
                                    UML kind: uml:Class */
                                }
                            }
                        }
                        package 'L3.1.2 Command and Data Handling Subsystem Rqts' {
                            doc /* Source XMI: _18_4_1_3880181_1492799702463_465822_45666
                            Comment _19_0_2_3880181_1600872080550_101323_63398
                            The repository for Command and Data Handling subsystem Rqts.  To be populated by a mission-specific team.
                            UML kind: uml:Package */
                            part def 'Command and Data Handling Subsystem Rqts Group' {
                                @OfficialCSRMProfile::'Concerns and Requirements Profile'::'Group';
                                doc /* Source XMI: _18_5_1_3880181_1500216121749_921663_55302
                                Stereotype Group: Text=The Group provides the prefix and numbering scheme - which is easy to change., Id=CdSub_1
                                UML kind: uml:Class */
                                requirement def 'Requirement Name' {
                                    @OfficialCSRMProfile::'Concerns and Requirements Profile'::'SubsystemRequirement';
                                    doc /* Shall statement */
                                    comment /* Source XMI: _19_0_2_3880181_1561493582793_419885_61358
                                    Stereotype SubsystemRequirement: Text=Shall statement, Id=CdSub_1.1
                                    UML kind: uml:Class */
                                }
                            }
                        }
                        package 'L3.1.3 Communication Subsystem Rqts' {
                            doc /* Source XMI: _18_4_1_3880181_1492799771850_451892_45668
                            Comment _19_0_2_3880181_1600872344965_625373_63400
                            The repository for Commuication subsystem Rqts.  To be populated by a mission-specific team.
                            UML kind: uml:Package */
                            part def 'Communication Subsystem Rqts Group' {
                                @OfficialCSRMProfile::'Concerns and Requirements Profile'::'Group';
                                doc /* Source XMI: _18_5_1_3880181_1500216431042_620995_55372
                                Stereotype Group: Text=The Group provides the prefix and numbering scheme - which is easy to change., Id=CmSub_1
                                UML kind: uml:Class */
                                requirement def 'Requirement Name' {
                                    @OfficialCSRMProfile::'Concerns and Requirements Profile'::'SubsystemRequirement';
                                    doc /* Shall statement */
                                    comment /* Source XMI: _19_0_2_3880181_1561493671831_156590_61389
                                    Stereotype SubsystemRequirement: Text=Shall statement, Id=CmSub_1.1
                                    UML kind: uml:Class */
                                }
                            }
                        }
                        package 'L3.1.4 Attitude Determination and Control Subsystem Rqts' {
                            doc /* Source XMI: _18_4_1_3880181_1492799826579_961674_45669
                            Comment _19_0_2_3880181_1600872222692_22972_63399
                            The repository for Attitude Determination and Control subsystem Rqts.  To be populated by a mission-specific team.
                            UML kind: uml:Package */
                            part def 'Attitude Determination and Control Subsystem Rqts Group' {
                                @OfficialCSRMProfile::'Concerns and Requirements Profile'::'Group';
                                doc /* Source XMI: _18_5_1_3880181_1500229037908_641856_55868
                                Stereotype Group: Text=The Group provides the prefix and numbering scheme - which is easy to change., Id=AdSub_1
                                UML kind: uml:Class */
                                requirement def 'Requirement Name' {
                                    @OfficialCSRMProfile::'Concerns and Requirements Profile'::'SubsystemRequirement';
                                    doc /* Shall statement */
                                    comment /* Source XMI: _19_0_2_3880181_1561493811608_146166_61434
                                    Stereotype SubsystemRequirement: Text=Shall statement, Id=AdSub_1.1
                                    UML kind: uml:Class */
                                }
                            }
                        }
                        package 'L3.1.5 Guidance Navigation and Control Subsystem Rqts' {
                            doc /* Source XMI: _18_4_1_3880181_1492799847535_690145_45670
                            Comment _19_0_2_3880181_1600872471082_196143_63501
                            The repository for Guidance Navigation and Control subsystem Rqts.  To be populated by a mission-specific team.
                            UML kind: uml:Package */
                            part def 'Guidance Navigation and  Control Subsystem Rqts Group' {
                                @OfficialCSRMProfile::'Concerns and Requirements Profile'::'Group';
                                doc /* Source XMI: _18_5_1_3880181_1500229266276_203101_55920
                                Stereotype Group: Text=The Group provides the prefix and numbering scheme - which is easy to change., Id=GnSub_1
                                UML kind: uml:Class */
                                requirement def 'Requirement Name' {
                                    @OfficialCSRMProfile::'Concerns and Requirements Profile'::'SubsystemRequirement';
                                    doc /* Shall statement */
                                    comment /* Source XMI: _19_0_2_3880181_1561493870149_799509_61465
                                    Stereotype SubsystemRequirement: Text=Shall statement, Id=GnSub_1.1
                                    UML kind: uml:Class */
                                }
                            }
                        }
                        package 'L3.1.6 Structures and Mechanisms Subsystem Rqts' {
                            doc /* Source XMI: _18_4_1_3880181_1492799891292_199296_45671
                            Comment _19_0_2_3880181_1600872562346_140574_63502
                            The repository for Structures and Mechanisms subsystem Rqts.  To be populated by a mission-specific team.
                            UML kind: uml:Package */
                            part def 'Structures and Mechanisms Subsystem Rqts Group' {
                                @OfficialCSRMProfile::'Concerns and Requirements Profile'::'Group';
                                doc /* Source XMI: _18_5_1_3880181_1500229687928_284013_55972
                                Stereotype Group: Text=The Group provides the prefix and numbering scheme - which is easy to change., Id=SmSub_1
                                UML kind: uml:Class */
                                requirement def 'Requirement Name' {
                                    @OfficialCSRMProfile::'Concerns and Requirements Profile'::'SubsystemRequirement';
                                    doc /* Shall statement */
                                    comment /* Source XMI: _19_0_2_3880181_1561493964013_863278_61495
                                    Stereotype SubsystemRequirement: Text=Shall statement, Id=SmSub_1.1
                                    UML kind: uml:Class */
                                }
                            }
                        }
                        package 'L3.1.7 Power Subsystem Rqts' {
                            doc /* Source XMI: _18_4_1_3880181_1492799915343_367464_45672
                            Comment _19_0_2_3880181_1600872676550_190565_63503
                            The repository for Power subsystem Rqts.  To be populated by a mission-specific team.
                            UML kind: uml:Package */
                            part def 'Power Subsystems Rqts Group' {
                                @OfficialCSRMProfile::'Concerns and Requirements Profile'::'Group';
                                doc /* Source XMI: _18_5_1_3880181_1500229997877_136463_56060
                                Stereotype Group: Text=The Group provides the prefix and numbering scheme - which is easy to change., Id=PoSub_1
                                UML kind: uml:Class */
                                requirement def 'Requirement Name' {
                                    @OfficialCSRMProfile::'Concerns and Requirements Profile'::'SubsystemRequirement';
                                    doc /* Shall statement */
                                    comment /* Source XMI: _19_0_2_3880181_1561494020495_322415_61526
                                    Stereotype SubsystemRequirement: Text=Shall statement, Id=PoSub_1.1
                                    UML kind: uml:Class */
                                }
                            }
                        }
                        package 'L3.1.8 Thermal Subsystem Rqts' {
                            doc /* Source XMI: _18_4_1_3880181_1492799941691_708878_45673
                            Comment _19_0_2_3880181_1600872745675_67771_63504
                            The repository for Thermal subsystem Rqts.  To be populated by a mission-specific team.
                            UML kind: uml:Package */
                            part def 'Thermal Subsystem Rqts Group' {
                                @OfficialCSRMProfile::'Concerns and Requirements Profile'::'Group';
                                doc /* Source XMI: _18_5_1_3880181_1500230446758_124027_56246
                                Stereotype Group: Text=The Group provides the prefix and numbering scheme - which is easy to change., Id=ThSub_1
                                UML kind: uml:Class */
                                requirement def 'Requirement Name' {
                                    @OfficialCSRMProfile::'Concerns and Requirements Profile'::'SubsystemRequirement';
                                    doc /* Shall statement */
                                    comment /* Source XMI: _19_0_2_3880181_1561494101296_680051_61557
                                    Stereotype SubsystemRequirement: Text=Shall statement, Id=ThSub_1.1
                                    UML kind: uml:Class */
                                }
                            }
                        }
                        package 'L3.1.9 Propulsion Subsystem Rqts' {
                            doc /* Source XMI: _18_4_1_3880181_1492799977307_291720_45674
                            Comment _19_0_2_3880181_1600872809755_991673_63505
                            The repository for Propulsion subsystem Rqts.  To be populated by a mission-specific team.
                            UML kind: uml:Package */
                            part def 'Propulsion Subsystem Rqts Group' {
                                @OfficialCSRMProfile::'Concerns and Requirements Profile'::'Group';
                                doc /* Source XMI: _18_5_1_3880181_1500230604395_381947_56297
                                Stereotype Group: Text=The Group provides the prefix and numbering scheme - which is easy to change., Id=PrSub_1
                                UML kind: uml:Class */
                                requirement def 'Requirement Name' {
                                    @OfficialCSRMProfile::'Concerns and Requirements Profile'::'SubsystemRequirement';
                                    doc /* Shall statement */
                                    comment /* Source XMI: _19_0_2_3880181_1561494204517_939227_61588
                                    Stereotype SubsystemRequirement: Text=Shall statement, Id=PrSub_1.1
                                    UML kind: uml:Class */
                                }
                            }
                        }
                    }
                }
                package 'L1 Enterprise Rqts' {
                    doc /* Source XMI: _18_5_2_3880181_1532359433636_518168_66809
                    Comment _19_0_2_3880181_1600871070117_232596_63374
                    Repository for Enterprise Rqts.  To be populated by a mission-specific team.
                    UML kind: uml:Package */
                }
                package 'L5 CubeSat Deployer Interface Rqts' {
                    doc /* Source XMI: _18_5_2_3880181_1543956528936_889838_63175
                    Comment _19_0_2_3880181_1600883445983_91995_63203
                    The design and development of the mission specific CubeSat must satisfy the Rqts for interfacing with a CubeSat Deployer.
                    The CubeSat team must document incorporation and satisfaction of the interface Rqts.
                    Comment _19_0_3_2b0010b_1619533266740_930124_14430 (Explanation)
                    The design and development of the mission specific CubeSat must satisfy the requirements for interfacing with a CubeSat Deployer.
                    The CubeSat team must document incorporation and satisfaction of the interface requirements.
                    Typically, this would be a verification matrix that lists requirements with information such as id, description, source, verification method, verification status, and verification results.
                    Typically, verification matrices are implemented with a spreadsheet.
                    However, this verification information can be incorporated into attributes of a SysML requirement element and exported as a spreadsheet.
                    So … the mission-specific team needs to determine how to document and populate these interface requirements.  .
                    Comment _19_0_3_2b0010b_1619533266753_683834_14441 (Explanation)
                    These requirements use the DeployerInterfaceRequirement stereotype with the following properties:
                    Id   Name    Text
                    Source Document - CubeSat Deployer System interface specification
                    Source Paragraph
                    Satisfaction Status
                    Satisfied By - The satisfy relationship is used to assert that a model element corresponding to the design or implementation satisfies a particular requirement.
                    Verify Method -  Verification methods include inspection, analysis, demonstration, and test.
                    Verified By - The verify relationship is between a requirement and a test case or other model element that is used to verify the requirement is satisfied.
                    Comment _19_0_3_2b0010b_1619533266760_332117_14452 (Explanation)
                    These requirements are to be populated based on / extracted from The CubeSat Deployer System interface specification.
                    For example:
                    Cal Poly CubeSat Design Specification  or
                    NanoRacks Interface Design Document
                    The interface requirement categories and Ids can modified as needed to be consistent with the interface specifications.
                    Comment _19_0_3_2b0010b_1619533266766_631394_14463 (Explanation)
                    Having CubeSat Deployer Systems provide SysML models that contain the interface requirements would be very beneficial and will be pursued.
                    We have created SysML model of the Cal Poly CubeSat Design Specification, but it is not a Cal Poly product.
                    Comment _19_0_2_3880181_1637954427474_621508_57510
                    CubeSat Deployer Interface Rqts - Population
                    UML kind: uml:Package */
                    part def 'General' {
                        @OfficialCSRMProfile::'Concerns and Requirements Profile'::'Group';
                        doc /* Source XMI: _18_5_2_3880181_1544020120533_45182_63030
                        Stereotype Group: Text=Breaker, Id=CubeDplr_1
                        UML kind: uml:Class */
                        requirement def 'TBP' {
                            @OfficialCSRMProfile::'Concerns and Requirements Profile'::'DeployerRequirement';
                            doc /* To be populated */
                            comment /* Source XMI: _18_5_2_3880181_1544020493580_286952_63047
                            Stereotype DeployerRequirement: Text=To be populated, Id=CubeDplr_1.1
                            UML kind: uml:Class */
                        }
                    }
                    part def 'Mechanical' {
                        @OfficialCSRMProfile::'Concerns and Requirements Profile'::'Group';
                        doc /* Source XMI: _18_5_2_3880181_1544020419722_499252_63038
                        Stereotype Group: Text=Breaker, Id=CubeDplr_2
                        UML kind: uml:Class */
                        requirement def 'Structure' {
                            @OfficialCSRMProfile::'Concerns and Requirements Profile'::'DeployerRequirement';
                            doc /* Breaker */
                            comment /* Source XMI: _18_5_2_3880181_1544021965207_19447_63260
                            Stereotype DeployerRequirement: Text=Breaker, Id=CubeDplr_2.1
                            UML kind: uml:Class */
                            requirement def 'TBP' {
                                @OfficialCSRMProfile::'Concerns and Requirements Profile'::'DeployerRequirement';
                                doc /* To be populated */
                                comment /* Source XMI: _18_5_2_3880181_1544023412974_217880_63581
                                Stereotype DeployerRequirement: Text=To be populated, Id=CubeDplr_2.1.1
                                UML kind: uml:Class */
                            }
                        }
                        requirement def 'Mass' {
                            @OfficialCSRMProfile::'Concerns and Requirements Profile'::'DeployerRequirement';
                            doc /* Breaker */
                            comment /* Source XMI: _18_5_2_3880181_1544022047817_992595_63268
                            Stereotype DeployerRequirement: Text=Breaker, Id=CubeDplr_2.2
                            UML kind: uml:Class */
                            requirement def 'TBP' {
                                @OfficialCSRMProfile::'Concerns and Requirements Profile'::'DeployerRequirement';
                                doc /* To be populated */
                                comment /* Source XMI: _18_5_2_3880181_1544023492818_58875_63589
                                Stereotype DeployerRequirement: Text=To be populated, Id=CubeDplr_2.2.1
                                UML kind: uml:Class */
                            }
                        }
                    }
                    part def 'Electrical' {
                        @OfficialCSRMProfile::'Concerns and Requirements Profile'::'Group';
                        doc /* Source XMI: _18_5_2_3880181_1544020508862_204228_63055
                        Stereotype Group: Text=Breaker, Id=CubeDplr_3
                        UML kind: uml:Class */
                        requirement def 'TBP' {
                            @OfficialCSRMProfile::'Concerns and Requirements Profile'::'DeployerRequirement';
                            doc /* To be populated */
                            comment /* Source XMI: _18_5_2_3880181_1544023334895_228582_63573
                            Stereotype DeployerRequirement: Text=To be populated, Id=CubeDplr_3.1
                            UML kind: uml:Class */
                        }
                    }
                    part def 'Environmental' {
                        @OfficialCSRMProfile::'Concerns and Requirements Profile'::'Group';
                        doc /* Source XMI: _18_5_2_3880181_1544021370691_399245_63197
                        Stereotype Group: Text=Breaker, Id=CubeDplr_4
                        UML kind: uml:Class */
                        requirement def 'Thermal' {
                            @OfficialCSRMProfile::'Concerns and Requirements Profile'::'DeployerRequirement';
                            doc /* Breaker */
                            comment /* Source XMI: _18_5_2_3880181_1544023261458_24125_63557
                            Stereotype DeployerRequirement: Text=Breaker, Id=CubeDplr_4.1
                            UML kind: uml:Class */
                            requirement def 'TBP' {
                                @OfficialCSRMProfile::'Concerns and Requirements Profile'::'DeployerRequirement';
                                doc /* To be populated */
                                comment /* Source XMI: _18_5_2_3880181_1544023610163_534980_63597
                                Stereotype DeployerRequirement: Text=To be populated, Id=CubeDplr_4.1.1
                                UML kind: uml:Class */
                            }
                        }
                        requirement def 'Vibration' {
                            @OfficialCSRMProfile::'Concerns and Requirements Profile'::'DeployerRequirement';
                            doc /* Breaker */
                            comment /* Source XMI: _18_5_2_3880181_1544023301755_424979_63565
                            Stereotype DeployerRequirement: Text=Breaker, Id=CubeDplr_4.2
                            UML kind: uml:Class */
                            requirement def 'TBP' {
                                @OfficialCSRMProfile::'Concerns and Requirements Profile'::'DeployerRequirement';
                                doc /* To be populated */
                                comment /* Source XMI: _18_5_2_3880181_1544023666256_812607_63605
                                Stereotype DeployerRequirement: Text=To be populated, Id=CubeDplr_4.2.1
                                UML kind: uml:Class */
                            }
                        }
                    }
                    part def 'Safety' {
                        @OfficialCSRMProfile::'Concerns and Requirements Profile'::'Group';
                        doc /* Source XMI: _18_5_2_3880181_1544021431129_515938_63205
                        Stereotype Group: Text=Breaker, Id=CubeDplr_6
                        UML kind: uml:Class */
                        requirement def 'TBP' {
                            @OfficialCSRMProfile::'Concerns and Requirements Profile'::'DeployerRequirement';
                            doc /* To be populated */
                            comment /* Source XMI: _18_5_2_3880181_1544023832990_984903_63621
                            Stereotype DeployerRequirement: Text=To be populated, Id=CubeDplr_6.1
                            UML kind: uml:Class */
                        }
                    }
                    part def 'Deployment' {
                        @OfficialCSRMProfile::'Concerns and Requirements Profile'::'Group';
                        doc /* Source XMI: _18_5_2_3880181_1544021465817_437532_63213
                        Stereotype Group: Text=Breaker, Id=CubeDplr_7
                        UML kind: uml:Class */
                        requirement def 'TBP' {
                            @OfficialCSRMProfile::'Concerns and Requirements Profile'::'DeployerRequirement';
                            doc /* To be populated */
                            comment /* Source XMI: _18_5_2_3880181_1544023860428_573499_63629
                            Stereotype DeployerRequirement: Text=To be populated, Id=CubeDplr_7.1
                            UML kind: uml:Class */
                        }
                    }
                    part def 'Materials' {
                        @OfficialCSRMProfile::'Concerns and Requirements Profile'::'Group';
                        doc /* Source XMI: _18_5_2_3880181_1544023084208_296963_63547
                        Stereotype Group: Text=Breaker, Id=CubeDplr_5
                        UML kind: uml:Class */
                        requirement def 'TBP' {
                            @OfficialCSRMProfile::'Concerns and Requirements Profile'::'DeployerRequirement';
                            doc /* To be populated */
                            comment /* Source XMI: _18_5_2_3880181_1544023772255_6583_63613
                            Stereotype DeployerRequirement: Text=To be populated, Id=CubeDplr_5.1
                            UML kind: uml:Class */
                        }
                    }
                }
            }
            package '2 - Technical Measures' {
                doc /* Source XMI: _18_5_2_3880181_1514819747685_920670_63005
                Comment _19_0_2_3880181_1600784866099_900680_62772
                Technical measures are an established set of measures based on the expectations and Rqts that are tracked and assessed to determine overall system effectiveness and stakeholder satisfaction.
                Stakeholders will likely describe their technical measures as text and captured in Technical Measure Specifications.
                Technical Measure Specifications have Traced To, Traced From, and Allocated To properties.
                They will communicate and negotiate these descriptions with engineers who will transform them into measures that can be tracked and assessed.
                Validation activities provide data to the technical measurement process that are used to assess how well the measures are either projected to meet, or are meeting, their stated value.
                UML kind: uml:Package */
                package '2.1 - Technical Measures - Specifications and Requirements - Population' {
                    doc /* Source XMI: _19_0_2_3880181_1636387510398_757978_55696
                    Comment _19_0_2_3880181_1636387510572_183490_55792
                    A Technical Measure provides a stakeholder insight into the definition and development of a technical solution.
                    Verification activities provide data to the technical measurement process that is used to assess how well the technical measure is either projected to meet, or is meeting, its stated value.
                    Common terms for these measures are MOEs, MOPs, and TPMs
                    MOEs are operational measures of success closely related to the achievement of the mission objective in the intended operational environment under a specified set of conditions.
                    MOPs are measures that characterize physical or functional attributes relating to system operation, measured or estimated under specified testing and/or operational environment conditions.
                    TPMs measure attributes of a system element to determine how well that element is satisfying, or expected to satisfy, a technical requirement.
                    Comment _19_0_2_3880181_1636387510572_102763_55793 (Explanation)
                    xxxx A Technical Measure is incorporated in to CubeSat Reference Model as a block value property based on the Technical Measure as specified by a stakeholder.
                    A stakeholder is going to most likely “describe” their Technical Measure in a document.  A stakeholder will communicate and negotiate their Technical Measure with the engineers and engineers will transform those descriptions into a value property.
                    These stakeholder specified TMs are captured in the Technical Measures Specification package.
                    Comment _19_0_2_3880181_1636387510572_626141_55794 (Explanation)
                    MOPs are measures that characterize physical or functional attributes relating to system operation, measured or estimated under specified testing and/or operational environment conditions
                    Comment _19_0_2_3880181_1636387510572_606473_55795
                    A Technical Measure provides a stakeholder insight into the definition and development of a technical solution.
                    Verification activities provide data to the technical measurement process that is used to assess how well the technical measure is either projected to meet, or is meeting, its stated value.
                    Common terms for these measures are:
                    - MOE - Measure of Effectiveness
                    - MOP - Measure of Performance
                    - TPM - Technical Performance Measure
                    - KPP - Key Performance Parameter
                    Comment _19_0_2_3880181_1636387510572_952148_55796 (Explanation)
                    xxxx Technical Measure Specifications have Traced To, Traced From, Allocated To properties.
                    Comment _19_0_2_3880181_1636387510572_409865_55797 (Explanation)
                    MOEs are operational measures of success closely related to the achievement of the mission objective in the intended operational environment under a specified set of conditions
                    Comment _19_0_2_3880181_1636387510572_546134_55798 (HowTo)
                    Double-click on a Technical Measure table and then click on Add New to add a new Technical Measure to the containment tree and to the table.
                    Right click the new element in the table then left click Select in Containment Tree to navigate to the new element.
                    Comment _19_0_2_3880181_1636387510572_726393_55799 (Explanation)
                    TPMs measure attributes of a system element to determine how well that element is satisfying, or expected to satisfy, a technical requirement
                    Comment _19_0_2_3880181_1636724536835_804872_56189 (Explanation)
                    xxxx Allocated To: Block (Enterprise, Segment, Subsystem), if a qualitative Technical Measure
                    Comment _19_0_2_3880181_1636724664792_513035_56195 (Explanation)
                    xxxx Traced From: Block (Enterprise, Segment, Subsystem) Threshold _Value, if a quantitative Technical Measure
                    Comment _19_0_2_3880181_1636724943040_947009_56249 (Explanation)
                    KPPs are measures that are critical and failure to meet threshold performance will result in reevaluation of a technical solution and with the possibility of project termination.
                    Comment _19_0_2_3880181_1637271783478_475116_55706 (Explanation)
                    Technical Measures - Specifications and Requirements - Population
                    Comment _19_0_2_3880181_1641150397420_260024_59013 (Explanation)
                    A Technical Measure is incorporated in to CubeSat System Reference Model as a block value property based on the Technical Measure as specified by a stakeholder
                    A stakeholder is going to most likely “describe” their Technical Measure in a document.  A stakeholder will communicate and negotiate their Technical Measure with the engineers and engineers will transform the description into a value property, and methods for calculating the value property.
                    The Technical Measures are captured in Technical Measures Specification packages and Technical Measurers Requirement packages.
                    Technical Measures Specification package diagrams are used to establish the relationships of Specifications, Methods, and Requirements.
                    Comment _19_0_2_3880181_1641150688495_505749_59026 (Explanation)
                    The Technical Measures Methods document iis part of the model and can be edited within the model.
                    It can be created externally and copy/pasted into a  Technical Measure package diagram for populatiion into the containment tree.
                    The Methods can be be incorporated into the Constraint block Constraints and Parameters compartments.
                    Parametric diagrams show how the constraint properties are connected.
                    UML kind: uml:Package */
                    package '2.1.1 MOE' {
                        doc /* Source XMI: _19_0_2_3880181_1636387510398_734036_55697
                        Comment _19_0_2_3880181_1636387510635_692691_55833
                        Repository for MOEs
                        UML kind: uml:Package */
                        package '2.1.1.1 MOE Specifications' {
                            doc /* Source XMI: _19_0_2_3880181_1639417985290_868805_56838
                            Comment _19_0_2_3880181_1640885278249_582300_57859
                            MoeA Methods.docx
                            Comment _19_0_2_3880181_1640890851803_36409_58290
                            MoeB Methods.docx
                            UML kind: uml:Package */
                            part def 'MoeA Specification' {
                                @OfficialCSRMProfile::'Technical Measures Profile'::'moeSpecification';
                                doc /* Source XMI: _19_0_2_3880181_1636387510572_262637_55801
                                Stereotype moeSpecification: summary=The system shall exhibit the property "MOE Name" that has a minimum of x and maximum of y,
                                Comment _19_0_2_3880181_1641238341956_841688_59222
                                Technical measure description
                                UML kind: uml:Class */
                            }
                            dependency relationship_3 from OfficialCSRM::'Data'::'01 - CubeSat System Reference Model'::'2 - Technical Measures'::'2.1 - Technical Measures - Specifications and Requirements - Population'::'2.1.1 MOE'::'2.1.1.1 MOE Specifications'::'MoeA Specification' to OfficialCSRM::'Data'::'01 - CubeSat System Reference Model'::'2 - Technical Measures'::'2.1 - Technical Measures - Specifications and Requirements - Population'::'2.1.1 MOE'::'2.1.1.2 MOE Requirements'::'MoeA Requirement' {
                                doc /* Source XMI: _19_0_2_3880181_1640889683683_999786_57928
                                Stereotype Refine
                                UML kind: uml:Abstraction */
                            }
                            part def 'MoeB Specification' {
                                @OfficialCSRMProfile::'Technical Measures Profile'::'moeSpecification';
                                doc /* Source XMI: _19_0_2_3880181_1640890405896_924459_58049
                                Stereotype moeSpecification: Id=
                                Comment _19_0_2_3880181_1641238438066_742265_59266
                                Technical measure description
                                UML kind: uml:Class */
                            }
                            dependency relationship_5 from OfficialCSRM::'Data'::'01 - CubeSat System Reference Model'::'2 - Technical Measures'::'2.1 - Technical Measures - Specifications and Requirements - Population'::'2.1.1 MOE'::'2.1.1.1 MOE Specifications'::'MoeB Specification' to OfficialCSRM::'Data'::'01 - CubeSat System Reference Model'::'2 - Technical Measures'::'2.1 - Technical Measures - Specifications and Requirements - Population'::'2.1.1 MOE'::'2.1.1.2 MOE Requirements'::'MoeB Requirement' {
                                doc /* Source XMI: _19_0_2_3880181_1640890511416_885986_58069
                                Stereotype Refine
                                UML kind: uml:Abstraction */
                            }
                            dependency relationship_6 from OfficialCSRM::'Data'::'01 - CubeSat System Reference Model'::'2 - Technical Measures'::'2.1 - Technical Measures - Specifications and Requirements - Population'::'2.1.1 MOE'::'2.1.1.1 MOE Specifications'::'MoeA Specification' to OfficialCSRM::'Data'::'01 - CubeSat System Reference Model'::'2 - Technical Measures'::'2.1 - Technical Measures - Specifications and Requirements - Population'::'2.1.1 MOE'::'2.1.1.2 MOE Requirements'::'MoeA Requirement' {
                                doc /* Source XMI: _19_0_2_3880181_1640979107726_954282_59123
                                Stereotype Refine
                                UML kind: uml:Abstraction */
                            }
                            dependency relationship_7 from OfficialCSRM::'Data'::'01 - CubeSat System Reference Model'::'2 - Technical Measures'::'2.1 - Technical Measures - Specifications and Requirements - Population'::'2.1.1 MOE'::'2.1.1.1 MOE Specifications'::'MoeB Specification' to OfficialCSRM::'Data'::'01 - CubeSat System Reference Model'::'2 - Technical Measures'::'2.1 - Technical Measures - Specifications and Requirements - Population'::'2.1.1 MOE'::'2.1.1.2 MOE Requirements'::'MoeB Requirement' {
                                doc /* Source XMI: _19_0_2_3880181_1641060126355_872138_58393
                                Stereotype Refine
                                UML kind: uml:Abstraction */
                            }
                        }
                        package '2.1.1.2 MOE Requirements' {
                            doc /* Source XMI: _19_0_2_3880181_1639418036726_664703_56839
                            UML kind: uml:Package */
                            requirement def 'MoeA Requirement' {
                                @OfficialCSRMProfile::'Technical Measures Profile'::'moeRequirement';
                                doc /* Shall statement */
                                comment /* Source XMI: _19_0_2_3880181_1639418195867_474428_56840
                                Stereotype moeRequirement: Text=Shall statement, Id=1
                                UML kind: uml:Class */
                            }
                            requirement def 'MoeB Requirement' {
                                @OfficialCSRMProfile::'Technical Measures Profile'::'moeRequirement';
                                doc /* Shall statement */
                                comment /* Source XMI: _19_0_2_3880181_1640890459085_928753_58061
                                Stereotype moeRequirement: Text=Shall statement, Id=2
                                UML kind: uml:Class */
                            }
                        }
                    }
                    package '2.1.2 MOP' {
                        doc /* Source XMI: _19_0_2_3880181_1636387510398_12619_55698
                        Comment _19_0_2_3880181_1636387510681_312348_55867
                        Repository for MOPs.
                        UML kind: uml:Package */
                        package '2.1.2.2 MOP Requirements' {
                            doc /* Source XMI: _19_0_2_3880181_1639425497415_119962_56897
                            UML kind: uml:Package */
                            requirement def 'MopA Requirement' {
                                @OfficialCSRMProfile::'Technical Measures Profile'::'mopRequirement';
                                doc /* Shall statement */
                                comment /* Source XMI: _19_0_2_3880181_1639426059464_157765_57068
                                Stereotype mopRequirement: Text=Shall statement, Id=1
                                UML kind: uml:Class */
                            }
                            requirement def 'MopB Requirement' {
                                @OfficialCSRMProfile::'Technical Measures Profile'::'mopRequirement';
                                doc /* Shall statement */
                                comment /* Source XMI: _19_0_2_3880181_1641086218348_651267_58530
                                Stereotype mopRequirement: Text=<html><body>Shall statement	</body></html>, Id=2
                                UML kind: uml:Class */
                            }
                        }
                        package '2.1.2.1 MOP Specifications' {
                            doc /* Source XMI: _19_0_2_3880181_1639425375450_301067_56896
                            Comment _19_0_2_3880181_1641060189918_646571_58459
                            MopA Methods.docx
                            Comment _19_0_2_3880181_1641088077678_255142_59264
                            MopB Methods.docx
                            UML kind: uml:Package */
                            part def 'MopA Specification' {
                                @OfficialCSRMProfile::'Technical Measures Profile'::'mopSpecification';
                                doc /* Source XMI: _19_0_2_3880181_1636387510635_112212_55836
                                Stereotype mopSpecification
                                Comment _19_0_2_3880181_1641238690300_601481_59346
                                Technical measure description
                                UML kind: uml:Class */
                            }
                            dependency relationship_3 from OfficialCSRM::'Data'::'01 - CubeSat System Reference Model'::'2 - Technical Measures'::'2.1 - Technical Measures - Specifications and Requirements - Population'::'2.1.2 MOP'::'2.1.2.1 MOP Specifications'::'MopA Specification' to OfficialCSRM::'Data'::'01 - CubeSat System Reference Model'::'2 - Technical Measures'::'2.1 - Technical Measures - Specifications and Requirements - Population'::'2.1.2 MOP'::'2.1.2.2 MOP Requirements'::'MopA Requirement' {
                                doc /* Source XMI: _19_0_2_3880181_1640978847584_874961_58974
                                Stereotype Refine
                                UML kind: uml:Abstraction */
                            }
                            dependency relationship_4 from OfficialCSRM::'Data'::'01 - CubeSat System Reference Model'::'2 - Technical Measures'::'2.1 - Technical Measures - Specifications and Requirements - Population'::'2.1.2 MOP'::'2.1.2.1 MOP Specifications'::'MopA Specification' to OfficialCSRM::'Data'::'01 - CubeSat System Reference Model'::'2 - Technical Measures'::'2.1 - Technical Measures - Specifications and Requirements - Population'::'2.1.2 MOP'::'2.1.2.2 MOP Requirements'::'MopA Requirement' {
                                doc /* Source XMI: _19_0_2_3880181_1640978935641_360052_58983
                                Stereotype Refine
                                UML kind: uml:Abstraction */
                            }
                            part def 'MopB Specification' {
                                @OfficialCSRMProfile::'Technical Measures Profile'::'mopSpecification';
                                doc /* Source XMI: _19_0_2_3880181_1641086056782_808571_58519
                                Stereotype mopSpecification: Id=
                                Comment _19_0_2_3880181_1641238698129_479304_59347
                                Technical measure description
                                UML kind: uml:Class */
                            }
                            dependency relationship_6 from OfficialCSRM::'Data'::'01 - CubeSat System Reference Model'::'2 - Technical Measures'::'2.1 - Technical Measures - Specifications and Requirements - Population'::'2.1.2 MOP'::'2.1.2.1 MOP Specifications'::'MopB Specification' to OfficialCSRM::'Data'::'01 - CubeSat System Reference Model'::'2 - Technical Measures'::'2.1 - Technical Measures - Specifications and Requirements - Population'::'2.1.2 MOP'::'2.1.2.2 MOP Requirements'::'MopB Requirement' {
                                doc /* Source XMI: _19_0_2_3880181_1641086280177_84502_58538
                                Stereotype Refine
                                UML kind: uml:Abstraction */
                            }
                            dependency relationship_7 from OfficialCSRM::'Data'::'01 - CubeSat System Reference Model'::'2 - Technical Measures'::'2.1 - Technical Measures - Specifications and Requirements - Population'::'2.1.2 MOP'::'2.1.2.1 MOP Specifications'::'MopB Specification' to OfficialCSRM::'Data'::'01 - CubeSat System Reference Model'::'2 - Technical Measures'::'2.1 - Technical Measures - Specifications and Requirements - Population'::'2.1.2 MOP'::'2.1.2.2 MOP Requirements'::'MopB Requirement' {
                                doc /* Source XMI: _19_0_2_3880181_1641088135761_443324_59290
                                Stereotype Refine
                                UML kind: uml:Abstraction */
                            }
                        }
                    }
                    package '2.1.3 TPM' {
                        doc /* Source XMI: _19_0_2_3880181_1636387510398_677959_55699
                        Comment _19_0_2_3880181_1636387510728_437811_55900
                        Repository for TPMs
                        UML kind: uml:Package */
                        package '2.1.3.1 TPM Specifications' {
                            doc /* Source XMI: _19_0_2_3880181_1639426505822_578509_57184
                            Comment _19_0_2_3880181_1641086762062_340469_58612
                            TpmA Methods.docx
                            Comment _19_0_2_3880181_1641134714371_971982_58593
                            TpmB Methods.docx
                            UML kind: uml:Package */
                            part def 'TpmA Specification' {
                                @OfficialCSRMProfile::'Technical Measures Profile'::'tpmSpecification';
                                doc /* Source XMI: _19_0_2_3880181_1636387510681_890687_55869
                                Stereotype tpmSpecification
                                Comment _19_0_2_3880181_1641238988863_881891_59440
                                Technical measure description
                                UML kind: uml:Class */
                            }
                            dependency relationship_3 from OfficialCSRM::'Data'::'01 - CubeSat System Reference Model'::'2 - Technical Measures'::'2.1 - Technical Measures - Specifications and Requirements - Population'::'2.1.3 TPM'::'2.1.3.1 TPM Specifications'::'TpmA Specification' to OfficialCSRM::'Data'::'01 - CubeSat System Reference Model'::'2 - Technical Measures'::'2.1 - Technical Measures - Specifications and Requirements - Population'::'2.1.3 TPM'::'2.1.3.2 TPM Requirements'::'TpmA Requirement' {
                                doc /* Source XMI: _19_0_2_3880181_1640978118184_715139_58750
                                Stereotype Refine
                                UML kind: uml:Abstraction */
                            }
                            dependency relationship_4 from OfficialCSRM::'Data'::'01 - CubeSat System Reference Model'::'2 - Technical Measures'::'2.1 - Technical Measures - Specifications and Requirements - Population'::'2.1.3 TPM'::'2.1.3.1 TPM Specifications'::'TpmA Specification' to OfficialCSRM::'Data'::'01 - CubeSat System Reference Model'::'2 - Technical Measures'::'2.1 - Technical Measures - Specifications and Requirements - Population'::'2.1.3 TPM'::'2.1.3.2 TPM Requirements'::'TpmA Requirement' {
                                doc /* Source XMI: _19_0_2_3880181_1641048232312_451859_58140
                                Stereotype Refine
                                UML kind: uml:Abstraction */
                            }
                            part def 'TpmB Specification' {
                                @OfficialCSRMProfile::'Technical Measures Profile'::'tpmSpecification';
                                doc /* Source XMI: _19_0_2_3880181_1641086922717_230247_58652
                                Stereotype tpmSpecification: Id=
                                Comment _19_0_2_3880181_1641238998671_534179_59442
                                Technical measure description
                                UML kind: uml:Class */
                            }
                            dependency relationship_6 from OfficialCSRM::'Data'::'01 - CubeSat System Reference Model'::'2 - Technical Measures'::'2.1 - Technical Measures - Specifications and Requirements - Population'::'2.1.3 TPM'::'2.1.3.1 TPM Specifications'::'TpmB Specification' to OfficialCSRM::'Data'::'01 - CubeSat System Reference Model'::'2 - Technical Measures'::'2.1 - Technical Measures - Specifications and Requirements - Population'::'2.1.3 TPM'::'2.1.3.2 TPM Requirements'::'TpmB Requirement' {
                                doc /* Source XMI: _19_0_2_3880181_1641087141570_487929_58678
                                Stereotype Refine
                                UML kind: uml:Abstraction */
                            }
                            dependency relationship_7 from OfficialCSRM::'Data'::'01 - CubeSat System Reference Model'::'2 - Technical Measures'::'2.1 - Technical Measures - Specifications and Requirements - Population'::'2.1.3 TPM'::'2.1.3.1 TPM Specifications'::'TpmB Specification' to OfficialCSRM::'Data'::'01 - CubeSat System Reference Model'::'2 - Technical Measures'::'2.1 - Technical Measures - Specifications and Requirements - Population'::'2.1.3 TPM'::'2.1.3.2 TPM Requirements'::'TpmB Requirement' {
                                doc /* Source XMI: _19_0_2_3880181_1641239239391_918252_59491
                                Stereotype Refine
                                UML kind: uml:Abstraction */
                            }
                        }
                        package '2.1.3.2 TPM Requirements' {
                            doc /* Source XMI: _19_0_2_3880181_1639426698510_210074_57189
                            UML kind: uml:Package */
                            requirement def 'TpmA Requirement' {
                                @OfficialCSRMProfile::'Technical Measures Profile'::'tpmRequirement';
                                doc /* Shall statement */
                                comment /* Source XMI: _19_0_2_3880181_1639426915951_819149_57198
                                Stereotype tpmRequirement: Text=Shall statement, Id=1
                                UML kind: uml:Class */
                            }
                            requirement def 'TpmB Requirement' {
                                @OfficialCSRMProfile::'Technical Measures Profile'::'tpmRequirement';
                                doc /* Shall statement */
                                comment /* Source XMI: _19_0_2_3880181_1641056363739_293120_58627
                                Stereotype tpmRequirement: Text=Shall statement, Id=2
                                UML kind: uml:Class */
                            }
                        }
                    }
                    package '2.1.4 KPP' {
                        doc /* Source XMI: _19_0_2_3880181_1636387510398_57495_55700
                        UML kind: uml:Package */
                        package '2.1.4.1 KPP Specifications' {
                            doc /* Source XMI: _19_0_2_3880181_1639427130329_864548_57311
                            Comment _19_0_2_3880181_1641137593495_475536_59094
                            KppA Methods.docx
                            Comment _19_0_2_3880181_1641258268958_234925_58576
                            KppB Methods.docx
                            UML kind: uml:Package */
                            part def 'KppA Specification' {
                                @OfficialCSRMProfile::'Technical Measures Profile'::'kppSpecification';
                                doc /* Source XMI: _19_0_2_3880181_1636392204795_245336_57575
                                Stereotype kppSpecification: Id=
                                Comment _19_0_2_3880181_1641239476004_6582_59593
                                Technical measure description
                                UML kind: uml:Class */
                            }
                            dependency relationship_3 from OfficialCSRM::'Data'::'01 - CubeSat System Reference Model'::'2 - Technical Measures'::'2.1 - Technical Measures - Specifications and Requirements - Population'::'2.1.4 KPP'::'2.1.4.1 KPP Specifications'::'KppA Specification' to OfficialCSRM::'Data'::'01 - CubeSat System Reference Model'::'2 - Technical Measures'::'2.1 - Technical Measures - Specifications and Requirements - Population'::'2.1.4 KPP'::'2.1.4.2 KPP Requirements'::'KppA Requirement' {
                                doc /* Source XMI: _19_0_2_3880181_1640976917863_158146_58516
                                Stereotype Refine
                                UML kind: uml:Abstraction */
                            }
                            dependency relationship_4 from OfficialCSRM::'Data'::'01 - CubeSat System Reference Model'::'2 - Technical Measures'::'2.1 - Technical Measures - Specifications and Requirements - Population'::'2.1.4 KPP'::'2.1.4.1 KPP Specifications'::'KppA Specification' to OfficialCSRM::'Data'::'01 - CubeSat System Reference Model'::'2 - Technical Measures'::'2.1 - Technical Measures - Specifications and Requirements - Population'::'2.1.4 KPP'::'2.1.4.2 KPP Requirements'::'KppA Requirement' {
                                doc /* Source XMI: _19_0_2_3880181_1640977336098_259821_58559
                                Stereotype Refine
                                UML kind: uml:Abstraction */
                            }
                            dependency relationship_5 from OfficialCSRM::'Data'::'01 - CubeSat System Reference Model'::'2 - Technical Measures'::'2.1 - Technical Measures - Specifications and Requirements - Population'::'2.1.4 KPP'::'2.1.4.1 KPP Specifications'::'KppA Specification' to OfficialCSRM::'Data'::'01 - CubeSat System Reference Model'::'2 - Technical Measures'::'2.1 - Technical Measures - Specifications and Requirements - Population'::'2.1.4 KPP'::'2.1.4.2 KPP Requirements'::'KppA Requirement' {
                                doc /* Source XMI: _19_0_2_3880181_1640977591277_247213_58579
                                Stereotype Refine
                                UML kind: uml:Abstraction */
                            }
                            part def 'KppB Specification' {
                                @OfficialCSRMProfile::'Technical Measures Profile'::'kppSpecification';
                                doc /* Source XMI: _19_0_2_3880181_1641136932885_191193_58826
                                Stereotype kppSpecification: Id=
                                Comment _19_0_2_3880181_1641239482567_372568_59594
                                Technical measure description
                                UML kind: uml:Class */
                            }
                            dependency relationship_7 from OfficialCSRM::'Data'::'01 - CubeSat System Reference Model'::'2 - Technical Measures'::'2.1 - Technical Measures - Specifications and Requirements - Population'::'2.1.4 KPP'::'2.1.4.1 KPP Specifications'::'KppB Specification' to OfficialCSRM::'Data'::'01 - CubeSat System Reference Model'::'2 - Technical Measures'::'2.1 - Technical Measures - Specifications and Requirements - Population'::'2.1.4 KPP'::'2.1.4.2 KPP Requirements'::'KppB Requirement' {
                                doc /* Source XMI: _19_0_2_3880181_1641137036932_313325_58832
                                Stereotype Refine
                                UML kind: uml:Abstraction */
                            }
                            dependency relationship_8 from OfficialCSRM::'Data'::'01 - CubeSat System Reference Model'::'2 - Technical Measures'::'2.1 - Technical Measures - Specifications and Requirements - Population'::'2.1.4 KPP'::'2.1.4.1 KPP Specifications'::'KppB Specification' to OfficialCSRM::'Data'::'01 - CubeSat System Reference Model'::'2 - Technical Measures'::'2.1 - Technical Measures - Specifications and Requirements - Population'::'2.1.4 KPP'::'2.1.4.2 KPP Requirements'::'KppB Requirement' {
                                doc /* Source XMI: _19_0_2_3880181_1641258322639_376832_58601
                                Stereotype Refine
                                UML kind: uml:Abstraction */
                            }
                        }
                        package '2.1.4.2 KPP Requirements' {
                            doc /* Source XMI: _19_0_2_3880181_1639427383854_977438_57316
                            UML kind: uml:Package */
                            requirement def 'KppA Requirement' {
                                @OfficialCSRMProfile::'Technical Measures Profile'::'kppRequirement';
                                doc /* Shall statement */
                                comment /* Source XMI: _19_0_2_3880181_1639427668110_10024_57317
                                Stereotype kppRequirement: Text=Shall statement, Id=1
                                UML kind: uml:Class */
                            }
                            requirement def 'KppB Requirement' {
                                @OfficialCSRMProfile::'Technical Measures Profile'::'kppRequirement';
                                doc /* Shall statement */
                                comment /* Source XMI: _19_0_2_3880181_1641050628893_142701_58897
                                Stereotype kppRequirement: Text=Shall statement, Id=2
                                UML kind: uml:Class */
                            }
                        }
                        part def 'KppB Spedification' {
                            @OfficialCSRMProfile::'Technical Measures Profile'::'kppSpecification';
                            doc /* Source XMI: _19_0_2_3880181_1641052437130_31307_59249
                            Stereotype kppSpecification: Id=
                            UML kind: uml:Class */
                        }
                    }
                }
            }
            package '3 - Behaviors' {
                doc /* Source XMI: _18_5_2_3880181_1542314598483_352913_62864
                Comment _19_0_2_3880181_1600785325374_747651_62833
                Behaviors describe the functionality of a system in terms of how it is used to achieve the goals of its various users.
                The behaviors are the concepts of operations and operation concepts.
                A behavior can be specified by a Use Case description, a Use Case diagram, or an Activity diagram.
                The Behavior architecture levels are Enterprise, CubeSat, Ground System, CubeSat Subsystems, and Ground Subsystems.
                Comment _19_0_2_3880181_1638203712957_386769_56969 (Explanation)
                Behavior Architectures and Population
                UML kind: uml:Package */
                package '3.2 Behaviors - Use Cases - Activities - Population' {
                    doc /* Source XMI: _19_0_2_3880181_1594906074544_398063_62921
                    Comment _19_0_2_3880181_1600795354811_582354_63884
                    This package provides artifacts for establishing a relationship between a requirement and a behavior that refines the requirement.
                    The behavior can be:
                    Expressed a by text-based Use Case Description.
                    Captured in a Use Case Diagram
                    Refined by an Activity Diagram.
                    A Use Case Description can be simple narrative or have a more detailed format such as presented in our 2017 IEEE Aerospace paper:
                    Use Case Name, Scope, Primary Actor, Supporting Actor
                    Stakeholder, Precondition, Trigger, Postconditions
                    At each level there are:
                    Behavior packages containing Use Case Description and their listing table
                    Use Case packages containing Use Cases Diagrams and their listing table
                    Activity packages containing Activity Diagrams and their listing table
                    At each level there are:
                    Behavior packages containing Use Case Description documents and their listing table
                    Use Case packages containing Use Cases Diagrams and their listing table
                    Activity packages containing Activity Diagrams and their listing table
                    Comment _19_0_3_2b0010b_1619212079915_59749_6518 (Explanation)
                    The package provides artifacts for establishing a relationship between a requirement and a behavior that refines the requirement.
                    The behavior can be:
                    Expressed a by text-baed Behavior Description.
                    Captured in a Use Case Diagram
                    Refined by an Activity Diagram.
                    A Behavior Description can be simple narrative or have a more detailed format such as presented in our 2017 IEEE Aerospace paper:
                    Use Case Name      Scope              Primary Actor      Supporting Actor
                    Stakeholder            Precondition     Trigger                Postconditions
                    At each level there are:
                    Behavior packages containing Behavior Description and their listing table
                    Use Case packages containing Use Cases Diagrams and their listing table
                    Activity packages containing Activity Diagrams and their listing table
                    Comment _19_0_3_2b0010b_1619212079924_263075_6529 (Explanation)
                    As presented here, the CSRM has an example of population and relationships of requirements, behaviors, use cases, and activities.
                    They are only examples.
                    Mission modelers can populate and establish relationships to best serve their missions.
                    Comment _19_0_3_2b0010b_1619212079930_972947_6540 (HowTo)
                    To navigate to a package:
                    Right click on package icon
                    Scroll down to Selct in Containment Tree
                    To open table:
                    Double left click on table icon
                    Comment _19_0_2_3880181_1637272422188_240217_56124
                    Behaviors - Use Cases - Activities - Population
                    UML kind: uml:Package */
                }
                package '3.1 Architectures: Requirements Behaviors Structures' {
                    doc /* Source XMI: _19_0_2_3880181_1594907133045_27300_62939
                    Comment _19_0_2_3880181_1600796749349_511908_63895
                    The package architecture for requirements, structures, and behaviors at the enterprise, segment, and subsystem levels.
                    Comment _19_0_3_2b0010b_1619212304590_762617_6911 (Explanation)
                    Package architecture for requirements, behaviors, and structures at the enterprise, segment, and subsystem levels
                    Comment _19_0_2_3880181_1640193116297_33492_58196 (Explanation)
                    Requirements define the What.  Behaviors and Structures specify the How.
                    Structure diagrams capture the framwork that carry out the beahaviors.
                    Activity diagrams and use case diagrams are behavior diagrams.
                    UML kind: uml:Package */
                }
            }
            package '7 - Validation Verification' {
                doc /* Source XMI: _18_5_2_3880181_1555247729018_120649_65626
                Comment _19_0_2_3880181_1600787566868_172115_62952
                The verification activity element can be populated to describe the process for verifying an element, e.g. a requirement.
                For example, the process could include verification plans, procedures, execution, results, and status.
                The validation activity element can be populated to describe the process for validating an element, e.g. a Technical Measure or a Mission Objective
                UML kind: uml:Package */
                package '7.1 - Validation Activities' {
                    doc /* Source XMI: _18_5_2_3880181_1555247792497_543158_65627
                    Comment _19_0_2_3880181_1601051216610_397944_63169
                    Repository for validation activities.
                    Comment _19_0_3_2b0010b_1619539285990_672576_26539 (HowTo)
                    Instructions for adding a new Validation Activity
                    Double-click on  Activities table and then click on Add New to add a new Activity to the containment tree and to the table.
                    Right click the new element in the table then left click Select in Containment Tree to navigate to the new element.
                    Comment _19_0_3_2b0010b_1619539286004_522388_26561 (Explanation)
                    Validation confirms, by providing objective evidence, that the system, as-built (or as it will be built), satisfies the stakeholders’ needs, objectives, and moes. That is, the right system has been (or will be) built.
                    Comment _19_0_2_3880181_1638981012565_865887_56678 (HowTo)
                    Instructions for establishing a relationship between a Technical Measure and a Validation Activity
                    Open the Validation Activities Table
                    Add a new Validation Activity or locate an existing one
                    Double click in the Verifies cell of the Verification Activity element to reveal three ellipses.
                    Click on the ellipses.  Search for the applicable Technical Measure.
                    Click on the Plus Sign to move the Technical Measure from the List Tab to the Selected Elements column.
                    Click on OK to populate the Verifies cell of the Verification Activity element.
                    Comment _19_0_2_3880181_1638981700971_459219_56711 (Explanation)
                    Validation Activites - Population
                    Comment _19_0_2_3880181_1638999927248_193119_56655 (Problem)
                    Add New does not work
                    UML kind: uml:Package */
                    action def 'Validation Activity Example' {
                        @OfficialCSRMProfile::'Validation and Verification Profile'::'ValidationActivity';
                        doc /* Source XMI: _19_0_3_2b0010b_1613264261897_122790_61460
                        Stereotype ValidationActivity
                        UML kind: uml:Activity */
                        out item parameter_0 {
                            doc /* Source XMI: _19_0_3_2b0010b_1613264348176_255610_61463
                            UML parameter name: verdict
                            UML direction: return
                            UML type: http://www.omg.org/spec/SysML/20181001/SysML.xmi#SysML_dataType.VerdictKind */
                        }
                        action node_1 {
                            doc /* Source XMI: _19_0_3_2b0010b_1613264348217_136727_61465
                            UML node kind: uml:ActivityParameterNode
                            UML node name: verdict
                            UML behavior: (none)
                            UML parameter: _19_0_3_2b0010b_1613264348176_255610_61463 */
                        }
                    }
                }
                package '7.2 - Verification Activities' {
                    doc /* Source XMI: _18_5_2_3880181_1555247819176_491088_65628
                    Comment _19_0_2_3880181_1601051105797_584049_63168
                    Repository for verification activities.
                    Comment _19_0_3_2b0010b_1619539335247_87589_26602 (HowTo)
                    Instructions for adding a new Verification Activity
                    Double-click on the Activities table and then click on Add New to add a new Activity to the containment tree and to the table.
                    Right click the new element in the table then left click Select in Containment Tree to navigate to the new element.
                    Comment _19_0_3_2b0010b_1619539335256_303293_26613 (Explanation)
                    Verification confirms, by providing objective evidence, that the system and all its elements perform their intended functions and satisfy the requirements allocated to them. That is, the system has been built right.
                    Comment _19_0_2_3880181_1638982401847_684185_57083 (HowTo)
                    Instructions for establishing a relationship between a Requirement and a Validation Activity
                    Open Validation Activities Table below.
                    Add a new Validation Activity or locate an existing one.
                    Either
                    Double click in the Verified By cell of the Technical Measure element to reveal three ellipses.
                    Click on the ellipses.  Search for the applicable Validation Activity.
                    Click on the Plus Sign to move the Validation Activity from the List Tab to the Selected Elements column.
                    Click on OK to populate the Verified By cell of the Technical Measure element
                    Note that the Traced From cell was automatically populated.
                    Double click in the Verifies cell of the Verification Activity element to reveal three ellipses.
                    Click on the ellipses.  Search for the applicable Requirement
                    .
                    Click on the Plus Sign to move the Requirement from the List Tab to the Selected Elements column
                    .
                    Click on OK to populate the Verifies cell of the Verification Activity element.
                    Comment _19_0_2_3880181_1638985977495_454957_57259
                    Verification Activities - Population
                    Comment _19_0_2_3880181_1639001022428_934776_56913 (Problem)
                    Add New does not work properly
                    UML kind: uml:Package */
                    action def 'Verification Activity Example' {
                        @OfficialCSRMProfile::'Validation and Verification Profile'::'VerificationActivity';
                        @OfficialCSRMProfile::'Validation and Verification Profile'::'ValidationActivity';
                        doc /* Source XMI: _19_0_3_2b0010b_1613264154660_563618_61385
                        Stereotype TestCase
                        Stereotype VerificationActivity
                        Stereotype ValidationActivity
                        UML kind: uml:Activity */
                        out item parameter_0 {
                            doc /* Source XMI: _19_0_3_2b0010b_1613264154681_40313_61411
                            UML parameter name: verdict
                            UML direction: return
                            UML type: http://www.omg.org/spec/SysML/20181001/SysML.xmi#SysML_dataType.VerdictKind */
                        }
                        action node_5 {
                            doc /* Source XMI: _19_0_3_2b0010b_1613264154689_109306_61412
                            UML node kind: uml:ActivityParameterNode
                            UML node name: verdict
                            UML behavior: (none)
                            UML parameter: _19_0_3_2b0010b_1613264154681_40313_61411 */
                        }
                        action node_6 {
                            doc /* Source XMI: _19_0_3_2b0010b_1613325826291_303994_70986
                            UML node kind: uml:CallBehaviorAction
                            UML node name: Verification Step
                            UML behavior: (none)
                            UML parameter: (none) */
                        }
                        action node_7 {
                            doc /* Source XMI: _19_0_3_2b0010b_1613325849085_351178_71014
                            UML node kind: uml:CallBehaviorAction
                            UML node name: Verification Setup
                            UML behavior: (none)
                            UML parameter: (none) */
                        }
                        action node_8 {
                            doc /* Source XMI: _19_0_3_2b0010b_1613325864913_760776_71042
                            UML node kind: uml:InitialNode
                            UML node name: (unnamed)
                            UML behavior: (none)
                            UML parameter: (none) */
                        }
                        action node_9 {
                            doc /* Source XMI: _19_0_3_2b0010b_1613325878444_728180_71094
                            UML node kind: uml:CallBehaviorAction
                            UML node name: Verify Result
                            UML behavior: (none)
                            UML parameter: (none) */
                            out item pin_0 {
                                doc /* Source XMI: _19_0_3_2b0010b_1613325899089_176570_71133
                                UML pin name: output
                                UML type: http://www.omg.org/spec/SysML/20181001/SysML.xmi#SysML_dataType.VerdictKind */
                            }
                        }
                        succession controlFlow_1 first 'node_8' then 'node_7' {
                            doc /* Source XMI: _19_0_3_2b0010b_1613325867447_247743_71056
                            UML ControlFlow between indexed node endpoints.
                            Source-only uml:LiteralUnlimitedNatural _19_0_3_2b0010b_1613325867447_637046_71057: {"type": "uml:LiteralUnlimitedNatural", "id": "_19_0_3_2b0010b_1613325867447_637046_71057", "value": "1"} */
                        }
                        succession controlFlow_2 first 'node_7' then 'node_6' {
                            doc /* Source XMI: _19_0_3_2b0010b_1613325872375_687401_71077
                            UML ControlFlow between indexed node endpoints.
                            Source-only uml:LiteralUnlimitedNatural _19_0_3_2b0010b_1613325872376_516192_71078: {"type": "uml:LiteralUnlimitedNatural", "id": "_19_0_3_2b0010b_1613325872376_516192_71078", "value": "1"} */
                        }
                        succession controlFlow_3 first 'node_6' then 'node_9' {
                            doc /* Source XMI: _19_0_3_2b0010b_1613325895892_90361_71122
                            UML ControlFlow between indexed node endpoints.
                            Source-only uml:LiteralUnlimitedNatural _19_0_3_2b0010b_1613325895892_686240_71123: {"type": "uml:LiteralUnlimitedNatural", "id": "_19_0_3_2b0010b_1613325895892_686240_71123", "value": "1"} */
                        }
                        flow objectFlow_4 from 'node_9'.pin_0 to 'node_5' {
                            doc /* Source XMI: _19_0_3_2b0010b_1613325907120_647537_71159
                            UML ObjectFlow between indexed node or pin endpoints.
                            Source-only uml:LiteralUnlimitedNatural _19_0_3_2b0010b_1613325907121_662995_71160: {"type": "uml:LiteralUnlimitedNatural", "id": "_19_0_3_2b0010b_1613325907121_662995_71160", "value": "1"} */
                        }
                    }
                }
            }
            package '0 - CSRM Overview and Navigation' {
                doc /* Source XMI: _19_0_2_3880181_1560973178665_952492_60195
                Comment _19_0_2_3880181_1600977268443_41506_62836
                CSRM landing overview and navigation package
                Comment _19_0_3_2b0010b_1619899398111_560885_262 (Explanation)
                This package is used by the Dassault Systems tool to add properties used in Tables.
                Comment _19_0_3_2b0010b_1619899443683_59852_289 (Explanation)
                This package is used by the Dassault Systems tool.
                Comment _19_0_3_2b0010b_1619899462810_899537_302 (Explanation)
                This package contains the extentions used by the CSRM.
                Comment _19_0_3_2b0010b_1619899502883_942442_315 (Explanation)
                This package contains the glossary terms and acronyms used by the CSRM.
                UML kind: uml:Package */
            }
            package '6 - Data Models' {
                doc /* Source XMI: _18_4_3e4019a_1478204058692_942377_18245
                Comment _19_0_2_3880181_1600794639871_647239_63631
                The Data Models package is a repository for mission data structures developed by the mission-specific team
                UML kind: uml:Package */
                package 'L1_Enterprise Data Models' {
                    doc /* Source XMI: _18_4_3e4019a_1484250187430_373487_20637
                    UML kind: uml:Package */
                }
                package 'L2_Segment Data Models' {
                    doc /* Source XMI: _18_4_3e4019a_1484250246767_968319_20648
                    UML kind: uml:Package */
                    package 'L2.2_Ground Segment Data Models' {
                        doc /* Source XMI: _18_4_3e4019a_1484250249161_275445_20650
                        UML kind: uml:Package */
                    }
                    package 'L2.1_Space Segment Data Models' {
                        doc /* Source XMI: _18_4_3e4019a_1484250248536_22142_20649
                        UML kind: uml:Package */
                        package 'L2.1.1_CubeSat Data Models' {
                            doc /* Source XMI: _19_0_2_3880181_1561823378334_411574_61589
                            UML kind: uml:Package */
                        }
                    }
                }
                package 'L3_Subsystem Data Models' {
                    doc /* Source XMI: _18_4_3e4019a_1484250265273_491026_20651
                    UML kind: uml:Package */
                    package 'L3.2_Ground Subsystem Data Models' {
                        doc /* Source XMI: _18_4_3e4019a_1484250486719_861689_20652
                        UML kind: uml:Package */
                    }
                    package 'L3.1_Space Subsystem Data Models' {
                        doc /* Source XMI: _18_4_3e4019a_1484250486724_180906_20653
                        UML kind: uml:Package */
                    }
                }
            }
            package '8 - CSRM Population' {
                doc /* Source XMI: _19_0_2_3880181_1637090044706_162904_55722
                Comment _19_0_2_3880181_1638387996660_252831_56651
                CSRM elements to be populated by missoin team
                UML kind: uml:Package */
                package '8.1 - CSRM Population' {
                    doc /* Source XMI: _19_0_2_3880181_1637108662813_807374_55910
                    Comment _19_0_3_2b0010b_1619533110963_132608_14144 (Explanation)
                    Each population package contains the associated CSRM elements and tables residing in the containment tree.    The tables are used to add, delete, and modify the individual elements and to establish relationships between the elements.
                    UML kind: uml:Package */
                }
            }
        }
        package '02 - CSRM Elements, Examples and Illustrations' {
            doc /* Source XMI: _19_0_2_3880181_1612801394820_399636_62538
            Comment _19_0_3_2b0010b_1619897531064_593205_70559 (Explanation)
            This package contains CSRM examples and illustrations. This is provided to aid in development and to explain how to use the CSRM.
            Be careful to not use the elements in this package as part of your design. We suggest copying any element to the primary model.
            This section should be removed when not required for reference.
            Comment _19_0_3_2b0010b_1619903824566_133579_6257
            This package is used to segragate examples and population diagrams from the core of CSRM.
            UML kind: uml:Package */
            package '1 - Stakeholders' {
                doc /* Source XMI: _19_0_2_3880181_1612801601930_887796_62539
                Comment _19_0_2_3880181_1638718455285_79074_56589 (Explanation)
                Stakeholder Examples and Illustrations
                UML kind: uml:Package */
                package '1.1 Regulatory Agency Stakeholders' {
                    doc /* Source XMI: _19_0_2_3880181_1638653755909_726039_56268
                    UML kind: uml:Package */
                    package '1.1.1 - Regulatory Agency Stakeholders - Examples' {
                        doc /* Source XMI: _19_0_2_3880181_1638649189744_615559_57562
                        Comment _19_0_2_3880181_1638649189776_127086_57606
                        A mission specific team will add Regulatory Agencies Stakeholders as applicable.
                        UML kind: uml:Package */
                        part def '18th Space Control Squadron' {
                            @OfficialCSRMProfile::'Architecture Structures Profile'::'Stakeholder';
                            doc /* Source XMI: _19_0_2_3880181_1638649189744_493679_57563
                            Stereotype Stakeholder
                            Comment _19_0_2_3880181_1638649189776_545014_57608
                            18th Space Control Squadron (18SPCS) provides the capability to register a satellite with 18SPCS in support of identification, tracking, and conjunction services.
                            UML kind: uml:Class */
                            ref part 'property_1' : OfficialCSRM::'Data'::'02 - CSRM Elements, Examples and Illustrations'::'1 - Stakeholders'::'1.2 Mission Stakeholders'::'1.2.3 - Mission Stakeholders Requirements Relationships - Example'::'1.2.3.2 - Stakeholder Concerns'::'Stakeholder Concerns Group'::'Study mission object' {
                                doc /* Source XMI: _19_0_2_3880181_1638649189776_724616_57609
                                UML aggregation: none
                                UML association: _19_0_2_3880181_1638649189744_156471_57575 */
                            }
                        }
                        part def 'FAA Commercial Space Transportation' {
                            @OfficialCSRMProfile::'Architecture Structures Profile'::'Stakeholder';
                            doc /* Source XMI: _19_0_2_3880181_1638649189744_264279_57564
                            Stereotype Stakeholder
                            UML kind: uml:Class */
                            ref part 'property_0' : OfficialCSRM::'Data'::'02 - CSRM Elements, Examples and Illustrations'::'1 - Stakeholders'::'1.2 Mission Stakeholders'::'1.2.3 - Mission Stakeholders Requirements Relationships - Example'::'1.2.3.2 - Stakeholder Concerns'::'Stakeholder Concerns Group'::'Study mission object' {
                                doc /* Source XMI: _19_0_2_3880181_1638649189776_705490_57611
                                UML aggregation: none
                                UML association: _19_0_2_3880181_1638649189744_864867_57576 */
                            }
                        }
                        part def 'Federal Communications Commission (FCC)' {
                            @OfficialCSRMProfile::'Architecture Structures Profile'::'Stakeholder';
                            doc /* Source XMI: _19_0_2_3880181_1638649189744_268183_57565
                            Stereotype Stakeholder
                            Comment _19_0_2_3880181_1638649189776_269463_57613
                            Non-federal users apply for spectrum certification through the Federal Communication Commission (FCC). The FCC maintains one integrated policy and position on spectrum when representing the United States internationally with respect to the International Telecommunication Union- Radiocommunication Sector (ITU-R) and World Radio Conferences (WRC).
                            UML kind: uml:Class */
                        }
                        part def 'International Amateur Radio Union (IARU)' {
                            @OfficialCSRMProfile::'Architecture Structures Profile'::'Stakeholder';
                            doc /* Source XMI: _19_0_2_3880181_1638649189744_158878_57566
                            Stereotype Stakeholder
                            Comment _19_0_2_3880181_1638649189776_471222_57615
                            An international confederation of national amateur radio organizations that works closely with ITU to allocate frequency spectrum to amateur radio and amateur-radio satellite services.
                            UML kind: uml:Class */
                        }
                        part def 'International Telecommunication Union - Radiocommunication Sector (ITU-R) ' {
                            @OfficialCSRMProfile::'Architecture Structures Profile'::'Stakeholder';
                            doc /* Source XMI: _19_0_2_3880181_1638649189744_85290_57567
                            Stereotype Stakeholder
                            Comment _19_0_2_3880181_1638649189776_571878_57617
                            An international confederation of national amateur radio organizations that works closely with ITU to allocate frequency spectrum to amateur radio and amateur-radio satellite services.
                            UML kind: uml:Class */
                        }
                        part def 'International Traffic in Arm Regulation (ITAR)' {
                            @OfficialCSRMProfile::'Architecture Structures Profile'::'Stakeholder';
                            doc /* Source XMI: _19_0_2_3880181_1638649189744_896993_57568
                            Stereotype Stakeholder
                            UML kind: uml:Class */
                        }
                        part def 'Laser Clearinghouse (LCH)' {
                            @OfficialCSRMProfile::'Architecture Structures Profile'::'Stakeholder';
                            doc /* Source XMI: _19_0_2_3880181_1638649189744_789998_57569
                            Stereotype Stakeholder
                            UML kind: uml:Class */
                        }
                        part def 'NASA Orbital Debris Program Office' {
                            @OfficialCSRMProfile::'Architecture Structures Profile'::'Stakeholder';
                            doc /* Source XMI: _19_0_2_3880181_1638649189744_588708_57570
                            Stereotype Stakeholder
                            Comment _19_0_2_3880181_1638649189776_658309_57621
                            U.S. Government orbital debris mitigation standard practices.
                            NASA Orbital Debris Program Office - glossary description
                            U.S. Government orbital debris mitigation standard practices.
                            UML kind: uml:Class */
                        }
                        part def 'NASA Spectrum Guidance for Small Satellite Missions' {
                            @OfficialCSRMProfile::'Architecture Structures Profile'::'Stakeholder';
                            doc /* Source XMI: _19_0_2_3880181_1638649189744_723908_57571
                            Stereotype Stakeholder
                            Comment _19_0_2_3880181_1638649189776_918223_57623
                            The Spectrum Guidance document, applicable to all NASA small satellite missions (orbiting systems < 180 kg), provides spectrum policy and process guidance for NASA small satellite missions requiring the use of the electromagnetic spectrum for transmission, reception, or both..
                            NASA Spectrum Guidance for Small Satellite Missions - glossary description
                            UML kind: uml:Class */
                        }
                        part def 'NOAA Commercial Remote Sensing Regulatory Affairs Office ' {
                            @OfficialCSRMProfile::'Architecture Structures Profile'::'Stakeholder';
                            doc /* Source XMI: _19_0_2_3880181_1638649189744_715323_57572
                            Stereotype Stakeholder
                            Comment _19_0_2_3880181_1638649189776_490462_57625
                            U.S. laws, regulations, policies, and related information pertaining to the operation of private and commercial remote sensing satellite systems.
                            NOAA Commercial Remote Sensing Regulatory Affairs Office - glossary description
                            UML kind: uml:Class */
                        }
                        part def 'Space-Track' {
                            @OfficialCSRMProfile::'Architecture Structures Profile'::'Stakeholder';
                            doc /* Source XMI: _19_0_2_3880181_1638649189744_674212_57573
                            Stereotype Stakeholder
                            Comment _19_0_2_3880181_1638649189776_12106_57627
                            Space-Track.org promotes space flight safety, protection of the space environment and the peaceful use of space worldwide by sharing space situational awareness services and information. with U.S. and international satellite owners/operators, academia and other entities.
                            Services include Launch Conjunction Assessment, Launch Early Orbit Determination, Early Orbit Conjunction Assessment, Advanced Conjunction Assessment (On-Orbit), Advance Collision Avoidance (On-Orbit), Disposal/End-of-Life Support, Deorbit and Reentry Support.
                            UML kind: uml:Class */
                        }
                        part def 'United Nations Office for Outer Space Affairs (UNOOSA)' {
                            @OfficialCSRMProfile::'Architecture Structures Profile'::'Stakeholder';
                            doc /* Source XMI: _19_0_2_3880181_1638649189744_236333_57574
                            Stereotype Stakeholder
                            UML kind: uml:Class */
                        }
                        connection def association_13 {
                            doc /* Source XMI: _19_0_2_3880181_1638649189744_156471_57575
                            UML end details are in the source map (SysML v2 connector ends have fixed [1..1] multiplicity). */
                            end end1 : OfficialCSRM::'Data'::'02 - CSRM Elements, Examples and Illustrations'::'1 - Stakeholders'::'1.2 Mission Stakeholders'::'1.2.3 - Mission Stakeholders Requirements Relationships - Example'::'1.2.3.2 - Stakeholder Concerns'::'Stakeholder Concerns Group'::'Study mission object' {
                                doc /* Source XMI: _19_0_2_3880181_1638649189776_724616_57609
                                UML end name: (unnamed) */
                            }
                            end end2 : OfficialCSRM::'Data'::'02 - CSRM Elements, Examples and Illustrations'::'1 - Stakeholders'::'1.1 Regulatory Agency Stakeholders'::'1.1.1 - Regulatory Agency Stakeholders - Examples'::'18th Space Control Squadron' {
                                doc /* Source XMI: _19_0_2_3880181_1638649189776_324678_57630
                                UML end name: (unnamed) */
                            }
                        }
                        connection def association_14 {
                            doc /* Source XMI: _19_0_2_3880181_1638649189744_864867_57576
                            UML end details are in the source map (SysML v2 connector ends have fixed [1..1] multiplicity). */
                            end end1 : OfficialCSRM::'Data'::'02 - CSRM Elements, Examples and Illustrations'::'1 - Stakeholders'::'1.2 Mission Stakeholders'::'1.2.3 - Mission Stakeholders Requirements Relationships - Example'::'1.2.3.2 - Stakeholder Concerns'::'Stakeholder Concerns Group'::'Study mission object' {
                                doc /* Source XMI: _19_0_2_3880181_1638649189776_705490_57611
                                UML end name: (unnamed) */
                            }
                            end end2 : OfficialCSRM::'Data'::'02 - CSRM Elements, Examples and Illustrations'::'1 - Stakeholders'::'1.1 Regulatory Agency Stakeholders'::'1.1.1 - Regulatory Agency Stakeholders - Examples'::'FAA Commercial Space Transportation' {
                                doc /* Source XMI: _19_0_2_3880181_1638649189776_512370_57631
                                UML end name: (unnamed) */
                            }
                        }
                    }
                }
                package '1.2 Mission Stakeholders' {
                    doc /* Source XMI: _19_0_2_3880181_1638653867097_404684_56270
                    UML kind: uml:Package */
                    package '1.2.1 - Mission Stakeholders - Examples' {
                        doc /* Source XMI: _19_0_2_3880181_1637437790838_876379_55378
                        Comment _19_0_2_3880181_1638294520531_821471_56945
                        A mission specific team will add Mission Stakeholders as applicable.
                        UML kind: uml:Package */
                        part def 'Tester' {
                            @OfficialCSRMProfile::'Architecture Structures Profile'::'Stakeholder';
                            doc /* Source XMI: _19_0_2_3880181_1576787850964_287242_63794
                            Stereotype Stakeholder
                            Comment _19_0_2_3880181_1576789251801_178065_63828
                            An individual or group responsible for the verification and validation processes.
                            Verification is the confirmation, through the provision of objective evidence, that specified Rqts have been fulfilled.
                            Validation is the confirmation, through the provision of objective evidence, that the Rqts for a specified intented use in the intended operational environment have been fulfilled.
                            UML kind: uml:Class */
                        }
                        part def 'Supplier' {
                            @OfficialCSRMProfile::'Architecture Structures Profile'::'Stakeholder';
                            doc /* Source XMI: _19_0_2_3880181_1576787838769_864371_63790
                            Stereotype Stakeholder
                            Comment _19_0_2_3880181_1576789169221_143233_63823
                            An individual or organization that enters into an agreement with the acquirer for the supply of a product or service.
                            [1/ App. C]
                            UML kind: uml:Class */
                        }
                        part def 'Sponsor' {
                            @OfficialCSRMProfile::'Architecture Structures Profile'::'Stakeholder';
                            doc /* Source XMI: _19_0_2_3880181_1576787825135_544727_63786
                            Stereotype Stakeholder
                            Comment _19_0_2_3880181_1576789143519_470903_63822
                            An individual or organization that provides funding.
                            UML kind: uml:Class */
                        }
                        part def 'Satellite Tracking Service' {
                            @OfficialCSRMProfile::'Architecture Structures Profile'::'Stakeholder';
                            doc /* Source XMI: _19_0_2_3880181_1576787802042_374624_63782
                            Stereotype Stakeholder
                            UML kind: uml:Class */
                        }
                        part def 'Satellite Shipping Service' {
                            @OfficialCSRMProfile::'Architecture Structures Profile'::'Stakeholder';
                            doc /* Source XMI: _19_0_2_3880181_1576787767761_902131_63778
                            Stereotype Stakeholder
                            UML kind: uml:Class */
                        }
                        part def 'Project Manager' {
                            @OfficialCSRMProfile::'Architecture Structures Profile'::'Stakeholder';
                            doc /* Source XMI: _19_0_2_3880181_1576787747564_384586_63774
                            Stereotype Stakeholder
                            Comment _19_0_2_3880181_1576791540284_919488_63342
                            The indivdual responsible for managing project attributes including project plans; estimates; schedule; budget; project structure; staffing; resources; infrastructure; and risk factors.
                            [7/ Pg. 834]
                            UML kind: uml:Class */
                        }
                        part def 'Project Engineer' {
                            @OfficialCSRMProfile::'Architecture Structures Profile'::'Stakeholder';
                            doc /* Source XMI: _19_0_2_3880181_1576787727580_713870_63770
                            Stereotype Stakeholder
                            Comment _19_0_2_3880181_1576789096993_410458_63821
                            The individual responsible for managing product attributes including items such as Rqts allocation and flow-down; system architecture; structure of and interactions among technical teams; specialty engineering; integration; verification; and validation.
                            [7/ Pg. 834]
                            UML kind: uml:Class */
                        }
                        part def 'Mission Engineer' {
                            @OfficialCSRMProfile::'Architecture Structures Profile'::'Stakeholder';
                            doc /* Source XMI: _19_0_2_3880181_1576787675838_252265_63762
                            Stereotype Stakeholder
                            Comment _19_0_2_3880181_1576788967321_314409_63814
                            The individual responsible for specifying mission data collection and analysis that fulfills the needs and objectives of the stakeholders. Data collection is specified by Rqts, constraints, quality, and quantity.
                            UML kind: uml:Class */
                        }
                        part def 'Launch Provider' {
                            @OfficialCSRMProfile::'Architecture Structures Profile'::'Stakeholder';
                            doc /* Source XMI: _19_0_2_3880181_1576787499738_228726_63758
                            Stereotype Stakeholder
                            UML kind: uml:Class */
                        }
                        part def 'Launch Operator' {
                            @OfficialCSRMProfile::'Architecture Structures Profile'::'Stakeholder';
                            doc /* Source XMI: _19_0_2_3880181_1576787481144_705108_63754
                            Stereotype Stakeholder
                            UML kind: uml:Class */
                        }
                        part def 'Launch Integrator' {
                            @OfficialCSRMProfile::'Architecture Structures Profile'::'Stakeholder';
                            doc /* Source XMI: _19_0_2_3880181_1576787450364_651515_63750
                            Stereotype Stakeholder
                            UML kind: uml:Class */
                        }
                        part def 'Integrator' {
                            @OfficialCSRMProfile::'Architecture Structures Profile'::'Stakeholder';
                            doc /* Source XMI: _19_0_2_3880181_1576787416097_420991_63746
                            Stereotype Stakeholder
                            UML kind: uml:Class */
                        }
                        part def 'End User' {
                            @OfficialCSRMProfile::'Architecture Structures Profile'::'Stakeholder';
                            doc /* Source XMI: _19_0_2_3880181_1576787394988_358615_63742
                            Stereotype Stakeholder
                            UML kind: uml:Class */
                        }
                        part def 'Chief Scientist' {
                            @OfficialCSRMProfile::'Architecture Structures Profile'::'Stakeholder';
                            doc /* Source XMI: _19_0_2_3880181_1576787308379_733831_63721
                            Stereotype Stakeholder
                            UML kind: uml:Class */
                        }
                        part def 'Developer' {
                            @OfficialCSRMProfile::'Architecture Structures Profile'::'Stakeholder';
                            doc /* Source XMI: _19_0_2_3880181_1576787338795_260598_63725
                            Stereotype Stakeholder
                            Comment _19_0_2_3880181_1576788876291_547915_63807
                            An individual or group responsible for the development process. The development process creates or fabricates a system element confirming to that element's detailed description (Rqts, architecture, design, interfaces).
                            [1/ Para. 4.7]
                            UML kind: uml:Class */
                        }
                        part def 'Acquirer' {
                            @OfficialCSRMProfile::'Architecture Structures Profile'::'Stakeholder';
                            doc /* Source XMI: _19_0_2_3880181_1576787072612_39217_63664
                            Stereotype Stakeholder
                            Comment _19_0_2_3880181_1576788752636_602334_63801
                            An individual or organization that acquires a product or service from a supplier.
                            [1/ App. C]
                            UML kind: uml:Class */
                        }
                        part def 'Development Facility Guidelines Regulations Policies' {
                            @OfficialCSRMProfile::'Architecture Structures Profile'::'Stakeholder';
                            doc /* Source XMI: _19_0_2_3880181_1576787360160_760378_63729
                            Stereotype Stakeholder
                            UML kind: uml:Class */
                        }
                        part def 'Operator' {
                            @OfficialCSRMProfile::'Architecture Structures Profile'::'Stakeholder';
                            doc /* Source XMI: _19_0_2_3880181_1576787702588_662967_63766
                            Stereotype Stakeholder
                            Comment _19_0_2_3880181_1576789075522_238502_63820
                            An individual who contributes to the functionality of a system and draws on knowledge, skills, and procedures to contribute the function.
                            [1/ App. C]
                            UML kind: uml:Class */
                        }
                    }
                    package '1.2.2 - Mission Stakeholders - Requirements, Technical Measures, Use Cases - Illustration' {
                        doc /* Source XMI: _18_4_1_3880181_1496161607538_44739_52553
                        Comment _19_0_2_3880181_1600789451511_448681_63297
                        The CubeSat System Reference Model has model elements for:
                        - stakeholder(s), concern(s)
                        - mission need(s), mission objective(s), mission constraint(s)
                        - mission requirement(s)
                        These model elements and their relationships are mission and engineering methodology specific.
                        The mission and methodology may dictate starting with stakeholder concerns.
                        Or starting with mission objectives and mission constraints.
                        Or a simpler approach of starting with just mission Rqts.
                        This terminology is consistent with a number of well established and accepted references.  The user of the CSRM should establish terminology (and then model elements) as needed for their stakeholders and mission.
                        The CSRM provides a library of model elements but does not dictate what model elements and relationships to use
                        Comment _19_0_3_2b0010b_1619208977928_284406_2191 (Explanation)
                        A stakeholder concern can be manifest in many forms, such as in relation to one or more stakeholder needs, goals, expectations, responsibilities, requirements, design constraints, assumptions, dependencies, quality attributes, architecture decisions, risks or other issues pertaining to the system.
                        There can be a number of stakeholders and a number of concerns.
                        The needs, objectives, constraints, and requirements result from review, assessment, and integration of the varied concerns.
                        Comment _19_0_3_2b0010b_1619208977928_537556_2202 (Explanation)
                        The CubeSat System Reference Model has model elements for:
                        - stakeholder(s), concern(s)
                        - mission need(s), mission objective(s), mission constraint(s)
                        - mission requirement(s)
                        These model elements and their relationships are mission and engineering methodology specific.
                        The mission and methodology may dictate starting with stakeholder concerns
                        Or starting with mission objectives and mission constraints
                        Or a simpler approach of starting with just mission requirements
                        Comment _19_0_3_2b0010b_1619208977928_618866_2213 (Explanation)
                        This terminology is consistent with a number of well established and accepted references.  The user of the CSRM should establish terminology (and then model elements) as needed for their stakeholders and mission.
                        .
                        Comment _19_0_3_2b0010b_1619208977943_480645_2224 (Explanation)
                        The CSRM provides a library of model elements but does not dictate what model elements and relationships to use
                        Comment _19_0_3_2b0010b_1619208977943_259729_2235 (Explanation)
                        MoeSpecification, MopSpecification, and TpmSpecification stereotypes have been created for the CSRM
                        Comment _19_0_3_2b0010b_1619208977943_317879_2246 (Explanation)
                        StakeholderConcern, MissionNeed, MissionObjective, MissionConstraint, and MissionRequirement stereotypes have been created for the CSRM
                        Comment _19_0_3_2b0010b_1619208977943_10125_2257 (Explanation)
                        Technical Measures are based on the expectations and requirements that are assessed to determine system effectiveness and stakeholder satisfaction.
                        Comment _19_0_3_2b0010b_1619208977959_878291_2268 (Explanation)
                        Use Cases describes the functionality of a system in terms of how it is used to achieve the goals of its various users.
                        Comment _19_0_3_2b0010b_1619738046410_276136_46315 (Explanation)
                        Use of Derive Relationship
                        Derived requirements generally correspond to requirements at the next level of the system hierarchy. A simple example would be a vehicle acceleration requirement that is analyzed to derive requirements for engine power, etc.
                        Arrow points from derived retirement to source requirement
                        It is also used to represent a relationship between requirements at the same level of the hierarchy but at different levels of abstraction. For example, the hardware or software requirements that are originally specified by the systems engineering team may be analyzed by the hardware or software team to derive more detailed requirements that reflect additional implementation considerations or constraints. The more detailed requirements from the hardware or the software team may be related to the original requirements, specified by the system team, through derive relationships.
                        Comment _19_0_2_3880181_1637523163539_645271_55744 (Explanation)
                        Mission Stakeholders - Requirements, Technical Measures, Use Cases - Illustration
                        Comment _19_0_2_3880181_1637770424670_787213_56412 (Explanation)
                        A refine relationship reduces ambiguity in an element.  The arrow points from the  element with the more detailed representation to the elememt that is being refined.
                        Comment _19_0_2_3880181_1637872536242_41641_56921 (Explanation)
                        Derive relationship.  Arrow points to the source requirement.  The relationship between a derived requirement and source requirement is intended to be based on analysis
                        Comment _19_0_2_3880181_1640655597445_33844_57646
                        The relationships between elements are captured in the element specifications and containment tree.
                        Those relationships are displayed and maintained in diagrams and tables as shown below
                        UML kind: uml:Package */
                        part def 'Mission Constraint Name' {
                            @OfficialCSRMProfile::'Concerns and Requirements Profile'::'MissionConstraint';
                            doc /* Source XMI: _18_5_2_3880181_1510168323770_211549_65813
                            Stereotype MissionConstraint: Text=, Id=4
                            UML kind: uml:Class */
                        }
                        requirement def 'Segment Requirement Name' {
                            @OfficialCSRMProfile::'Concerns and Requirements Profile'::'SegmentRequirement';
                            comment /* Source XMI: _18_5_2_3880181_1510168720960_47387_65880
                            Stereotype SegmentRequirement: Text=, Id=6
                            UML kind: uml:Class */
                        }
                        requirement def 'Subsystem Requirement Name' {
                            @OfficialCSRMProfile::'Concerns and Requirements Profile'::'SubsystemRequirement';
                            comment /* Source XMI: _18_5_2_3880181_1510168916124_902356_65916
                            Stereotype SubsystemRequirement: Text=, Id=7
                            UML kind: uml:Class */
                        }
                        dependency relationship_17 from OfficialCSRM::'Data'::'02 - CSRM Elements, Examples and Illustrations'::'1 - Stakeholders'::'1.2 Mission Stakeholders'::'1.2.2 - Mission Stakeholders - Requirements, Technical Measures, Use Cases - Illustration'::'Mission Constraint Name' to OfficialCSRM::'Data'::'02 - CSRM Elements, Examples and Illustrations'::'1 - Stakeholders'::'1.2 Mission Stakeholders'::'1.2.2 - Mission Stakeholders - Requirements, Technical Measures, Use Cases - Illustration'::'Stakeholder Concern Name' {
                            doc /* Source XMI: _18_5_2_3880181_1510188871911_835834_64627
                            Stereotype DeriveReqt
                            UML kind: uml:Abstraction */
                        }
                        part def 'Measure of Effectiveness Name' {
                            @OfficialCSRMProfile::'Technical Measures Profile'::'moeSpecification';
                            doc /* Source XMI: _18_5_2_3880181_1510191947052_488806_64645
                            Stereotype moeSpecification
                            UML kind: uml:Class */
                        }
                        part def 'Measure of Performance Name' {
                            @OfficialCSRMProfile::'Technical Measures Profile'::'mopSpecification';
                            doc /* Source XMI: _18_5_2_3880181_1510192279006_459688_64678
                            Stereotype mopSpecification
                            UML kind: uml:Class */
                        }
                        part def 'Technical Performance Measure Name' {
                            @OfficialCSRMProfile::'Technical Measures Profile'::'tpmSpecification';
                            doc /* Source XMI: _18_5_2_3880181_1510192538895_499635_64774
                            Stereotype tpmSpecification
                            UML kind: uml:Class */
                        }
                        dependency relationship_21 from OfficialCSRM::'Data'::'02 - CSRM Elements, Examples and Illustrations'::'1 - Stakeholders'::'1.2 Mission Stakeholders'::'1.2.2 - Mission Stakeholders - Requirements, Technical Measures, Use Cases - Illustration'::'Measure of Performance Name' to OfficialCSRM::'Data'::'02 - CSRM Elements, Examples and Illustrations'::'1 - Stakeholders'::'1.2 Mission Stakeholders'::'1.2.2 - Mission Stakeholders - Requirements, Technical Measures, Use Cases - Illustration'::'Measure of Effectiveness Name' {
                            doc /* Source XMI: _18_5_2_3880181_1510192719826_277833_64824
                            Stereotype Refine
                            UML kind: uml:Abstraction */
                        }
                        dependency relationship_22 from OfficialCSRM::'Data'::'02 - CSRM Elements, Examples and Illustrations'::'1 - Stakeholders'::'1.2 Mission Stakeholders'::'1.2.2 - Mission Stakeholders - Requirements, Technical Measures, Use Cases - Illustration'::'Technical Performance Measure Name' to OfficialCSRM::'Data'::'02 - CSRM Elements, Examples and Illustrations'::'1 - Stakeholders'::'1.2 Mission Stakeholders'::'1.2.2 - Mission Stakeholders - Requirements, Technical Measures, Use Cases - Illustration'::'Measure of Performance Name' {
                            doc /* Source XMI: _18_5_2_3880181_1510192810056_783306_64849
                            Stereotype Refine
                            UML kind: uml:Abstraction */
                        }
                        dependency relationship_23 from OfficialCSRM::'Data'::'02 - CSRM Elements, Examples and Illustrations'::'1 - Stakeholders'::'1.2 Mission Stakeholders'::'1.2.2 - Mission Stakeholders - Requirements, Technical Measures, Use Cases - Illustration'::'Measure of Performance Name' to OfficialCSRM::'Data'::'02 - CSRM Elements, Examples and Illustrations'::'1 - Stakeholders'::'1.2 Mission Stakeholders'::'1.2.2 - Mission Stakeholders - Requirements, Technical Measures, Use Cases - Illustration'::'Segment Requirement Name' {
                            doc /* Source XMI: _19_0_2_3880181_1573069385222_905194_62845
                            Stereotype Refine
                            UML kind: uml:Abstraction */
                        }
                        dependency relationship_24 from OfficialCSRM::'Data'::'02 - CSRM Elements, Examples and Illustrations'::'1 - Stakeholders'::'1.2 Mission Stakeholders'::'1.2.2 - Mission Stakeholders - Requirements, Technical Measures, Use Cases - Illustration'::'Technical Performance Measure Name' to OfficialCSRM::'Data'::'02 - CSRM Elements, Examples and Illustrations'::'1 - Stakeholders'::'1.2 Mission Stakeholders'::'1.2.2 - Mission Stakeholders - Requirements, Technical Measures, Use Cases - Illustration'::'Subsystem Requirement Name' {
                            doc /* Source XMI: _19_0_2_3880181_1573069403647_204836_62855
                            Stereotype Refine
                            UML kind: uml:Abstraction */
                        }
                        requirement def 'Mission Requirement Name' {
                            @OfficialCSRMProfile::'Concerns and Requirements Profile'::'MissionRequirement';
                            comment /* Source XMI: _19_0_2_3880181_1637508502762_334579_55849
                            Stereotype MissionRequirement: Text=, Id=5
                            UML kind: uml:Class */
                        }
                        dependency relationship_26 from OfficialCSRM::'Data'::'02 - CSRM Elements, Examples and Illustrations'::'1 - Stakeholders'::'1.2 Mission Stakeholders'::'1.2.2 - Mission Stakeholders - Requirements, Technical Measures, Use Cases - Illustration'::'Segment Requirement Name' to OfficialCSRM::'Data'::'02 - CSRM Elements, Examples and Illustrations'::'1 - Stakeholders'::'1.2 Mission Stakeholders'::'1.2.2 - Mission Stakeholders - Requirements, Technical Measures, Use Cases - Illustration'::'Mission Requirement Name' {
                            doc /* Source XMI: _19_0_2_3880181_1637508824261_6746_55886
                            Stereotype DeriveReqt
                            UML kind: uml:Abstraction */
                        }
                        dependency relationship_27 from OfficialCSRM::'Data'::'02 - CSRM Elements, Examples and Illustrations'::'1 - Stakeholders'::'1.2 Mission Stakeholders'::'1.2.2 - Mission Stakeholders - Requirements, Technical Measures, Use Cases - Illustration'::'Measure of Effectiveness Name' to OfficialCSRM::'Data'::'02 - CSRM Elements, Examples and Illustrations'::'1 - Stakeholders'::'1.2 Mission Stakeholders'::'1.2.2 - Mission Stakeholders - Requirements, Technical Measures, Use Cases - Illustration'::'Mission Requirement Name' {
                            doc /* Source XMI: _19_0_2_3880181_1637509959762_678969_55922
                            Stereotype Refine
                            UML kind: uml:Abstraction */
                        }
                        dependency relationship_28 from OfficialCSRM::'Data'::'02 - CSRM Elements, Examples and Illustrations'::'1 - Stakeholders'::'1.2 Mission Stakeholders'::'1.2.2 - Mission Stakeholders - Requirements, Technical Measures, Use Cases - Illustration'::'Mission Requirement Name' to OfficialCSRM::'Data'::'02 - CSRM Elements, Examples and Illustrations'::'1 - Stakeholders'::'1.2 Mission Stakeholders'::'1.2.2 - Mission Stakeholders - Requirements, Technical Measures, Use Cases - Illustration'::'Mission Objective Name' {
                            doc /* Source XMI: _19_0_2_3880181_1637510078498_419246_55932
                            Stereotype DeriveReqt
                            UML kind: uml:Abstraction */
                        }
                        dependency relationship_29 from OfficialCSRM::'Data'::'02 - CSRM Elements, Examples and Illustrations'::'1 - Stakeholders'::'1.2 Mission Stakeholders'::'1.2.2 - Mission Stakeholders - Requirements, Technical Measures, Use Cases - Illustration'::'Mission Requirement Name' to OfficialCSRM::'Data'::'02 - CSRM Elements, Examples and Illustrations'::'1 - Stakeholders'::'1.2 Mission Stakeholders'::'1.2.2 - Mission Stakeholders - Requirements, Technical Measures, Use Cases - Illustration'::'Mission Constraint Name' {
                            doc /* Source XMI: _19_0_2_3880181_1637510647776_219772_55958
                            Stereotype DeriveReqt
                            UML kind: uml:Abstraction */
                        }
                        use case def 'Mission Use Case' {
                            doc /* Source XMI: _19_0_2_3880181_1637521350399_488523_55572
                            UML kind: uml:UseCase */
                        }
                        dependency relationship_31 from OfficialCSRM::'Data'::'02 - CSRM Elements, Examples and Illustrations'::'1 - Stakeholders'::'1.2 Mission Stakeholders'::'1.2.2 - Mission Stakeholders - Requirements, Technical Measures, Use Cases - Illustration'::'Mission Use Case' to OfficialCSRM::'Data'::'02 - CSRM Elements, Examples and Illustrations'::'1 - Stakeholders'::'1.2 Mission Stakeholders'::'1.2.2 - Mission Stakeholders - Requirements, Technical Measures, Use Cases - Illustration'::'Mission Requirement Name' {
                            doc /* Source XMI: _19_0_2_3880181_1637521500029_987515_55589
                            Stereotype Refine
                            UML kind: uml:Abstraction */
                        }
                        dependency relationship_32 from OfficialCSRM::'Data'::'02 - CSRM Elements, Examples and Illustrations'::'1 - Stakeholders'::'1.2 Mission Stakeholders'::'1.2.2 - Mission Stakeholders - Requirements, Technical Measures, Use Cases - Illustration'::'Segment Requirement Name' to OfficialCSRM::'Data'::'02 - CSRM Elements, Examples and Illustrations'::'1 - Stakeholders'::'1.2 Mission Stakeholders'::'1.2.2 - Mission Stakeholders - Requirements, Technical Measures, Use Cases - Illustration'::'Mission Use Case' {
                            doc /* Source XMI: _19_0_2_3880181_1637521555230_240881_55600
                            Stereotype Trace
                            UML kind: uml:Abstraction */
                        }
                        use case def 'Segment Use Case' {
                            doc /* Source XMI: _19_0_2_3880181_1637521774162_849447_55606
                            UML kind: uml:UseCase */
                        }
                        use case def 'Subsystem Use Case' {
                            doc /* Source XMI: _19_0_2_3880181_1637521800635_436464_55607
                            UML kind: uml:UseCase */
                        }
                        dependency relationship_35 from OfficialCSRM::'Data'::'02 - CSRM Elements, Examples and Illustrations'::'1 - Stakeholders'::'1.2 Mission Stakeholders'::'1.2.2 - Mission Stakeholders - Requirements, Technical Measures, Use Cases - Illustration'::'Segment Use Case' to OfficialCSRM::'Data'::'02 - CSRM Elements, Examples and Illustrations'::'1 - Stakeholders'::'1.2 Mission Stakeholders'::'1.2.2 - Mission Stakeholders - Requirements, Technical Measures, Use Cases - Illustration'::'Segment Requirement Name' {
                            doc /* Source XMI: _19_0_2_3880181_1637521885104_43979_55624
                            Stereotype Refine
                            UML kind: uml:Abstraction */
                        }
                        dependency relationship_36 from OfficialCSRM::'Data'::'02 - CSRM Elements, Examples and Illustrations'::'1 - Stakeholders'::'1.2 Mission Stakeholders'::'1.2.2 - Mission Stakeholders - Requirements, Technical Measures, Use Cases - Illustration'::'Subsystem Requirement Name' to OfficialCSRM::'Data'::'02 - CSRM Elements, Examples and Illustrations'::'1 - Stakeholders'::'1.2 Mission Stakeholders'::'1.2.2 - Mission Stakeholders - Requirements, Technical Measures, Use Cases - Illustration'::'Segment Use Case' {
                            doc /* Source XMI: _19_0_2_3880181_1637521980698_700630_55656
                            Stereotype Trace
                            UML kind: uml:Abstraction */
                        }
                        dependency relationship_37 from OfficialCSRM::'Data'::'02 - CSRM Elements, Examples and Illustrations'::'1 - Stakeholders'::'1.2 Mission Stakeholders'::'1.2.2 - Mission Stakeholders - Requirements, Technical Measures, Use Cases - Illustration'::'Subsystem Use Case' to OfficialCSRM::'Data'::'02 - CSRM Elements, Examples and Illustrations'::'1 - Stakeholders'::'1.2 Mission Stakeholders'::'1.2.2 - Mission Stakeholders - Requirements, Technical Measures, Use Cases - Illustration'::'Subsystem Requirement Name' {
                            doc /* Source XMI: _19_0_2_3880181_1637522121290_847241_55680
                            Stereotype Refine
                            UML kind: uml:Abstraction */
                        }
                        part def 'Stakeholder Name' {
                            @OfficialCSRMProfile::'Architecture Structures Profile'::'Stakeholder';
                            doc /* Source XMI: _19_0_2_3880181_1637522462655_226026_55691
                            Stereotype Stakeholder
                            UML kind: uml:Class */
                        }
                        part def 'Stakeholder Concern Name' {
                            @OfficialCSRMProfile::'Concerns and Requirements Profile'::'StakeholderConcern';
                            doc /* Source XMI: _18_5_2_3880181_1510167244240_897304_65706
                            Stereotype StakeholderConcern: Text=, Id=1
                            UML kind: uml:Class */
                        }
                        dependency relationship_40 from OfficialCSRM::'Data'::'02 - CSRM Elements, Examples and Illustrations'::'1 - Stakeholders'::'1.2 Mission Stakeholders'::'1.2.2 - Mission Stakeholders - Requirements, Technical Measures, Use Cases - Illustration'::'Stakeholder Concern Name' to OfficialCSRM::'Data'::'02 - CSRM Elements, Examples and Illustrations'::'1 - Stakeholders'::'1.2 Mission Stakeholders'::'1.2.2 - Mission Stakeholders - Requirements, Technical Measures, Use Cases - Illustration'::'Stakeholder Name' {
                            doc /* Source XMI: _19_0_2_3880181_1637523075274_484723_55735
                            Stereotype Trace
                            UML kind: uml:Abstraction */
                        }
                        part def 'Mission Need Name' {
                            @OfficialCSRMProfile::'Concerns and Requirements Profile'::'MissionNeed';
                            doc /* Source XMI: _18_5_2_3880181_1510167570592_983784_65745
                            Stereotype MissionNeed: Text=, Id=2
                            UML kind: uml:Class */
                        }
                        dependency relationship_42 from OfficialCSRM::'Data'::'02 - CSRM Elements, Examples and Illustrations'::'1 - Stakeholders'::'1.2 Mission Stakeholders'::'1.2.2 - Mission Stakeholders - Requirements, Technical Measures, Use Cases - Illustration'::'Mission Need Name' to OfficialCSRM::'Data'::'02 - CSRM Elements, Examples and Illustrations'::'1 - Stakeholders'::'1.2 Mission Stakeholders'::'1.2.2 - Mission Stakeholders - Requirements, Technical Measures, Use Cases - Illustration'::'Stakeholder Concern Name' {
                            doc /* Source XMI: _18_5_2_3880181_1510188566924_570525_64555
                            Stereotype DeriveReqt
                            UML kind: uml:Abstraction */
                        }
                        part def 'Mission Objective Name' {
                            @OfficialCSRMProfile::'Concerns and Requirements Profile'::'MissionObjective';
                            doc /* Source XMI: _18_5_2_3880181_1510167918020_310503_65779
                            Stereotype MissionObjective: Text=, Id=3
                            UML kind: uml:Class */
                        }
                        dependency relationship_44 from OfficialCSRM::'Data'::'02 - CSRM Elements, Examples and Illustrations'::'1 - Stakeholders'::'1.2 Mission Stakeholders'::'1.2.2 - Mission Stakeholders - Requirements, Technical Measures, Use Cases - Illustration'::'Mission Objective Name' to OfficialCSRM::'Data'::'02 - CSRM Elements, Examples and Illustrations'::'1 - Stakeholders'::'1.2 Mission Stakeholders'::'1.2.2 - Mission Stakeholders - Requirements, Technical Measures, Use Cases - Illustration'::'Measure of Effectiveness Name' {
                            doc /* Source XMI: _18_5_2_3880181_1510192678272_894164_64812
                            Stereotype Refine
                            UML kind: uml:Abstraction */
                        }
                        dependency relationship_45 from OfficialCSRM::'Data'::'02 - CSRM Elements, Examples and Illustrations'::'1 - Stakeholders'::'1.2 Mission Stakeholders'::'1.2.2 - Mission Stakeholders - Requirements, Technical Measures, Use Cases - Illustration'::'Mission Objective Name' to OfficialCSRM::'Data'::'02 - CSRM Elements, Examples and Illustrations'::'1 - Stakeholders'::'1.2 Mission Stakeholders'::'1.2.2 - Mission Stakeholders - Requirements, Technical Measures, Use Cases - Illustration'::'Mission Need Name' {
                            doc /* Source XMI: _18_5_2_3880181_1510188603337_764623_64567
                            Stereotype DeriveReqt
                            UML kind: uml:Abstraction */
                        }
                        dependency relationship_46 from OfficialCSRM::'Data'::'02 - CSRM Elements, Examples and Illustrations'::'1 - Stakeholders'::'1.2 Mission Stakeholders'::'1.2.2 - Mission Stakeholders - Requirements, Technical Measures, Use Cases - Illustration'::'Mission Objective Name' to OfficialCSRM::'Data'::'02 - CSRM Elements, Examples and Illustrations'::'1 - Stakeholders'::'1.2 Mission Stakeholders'::'1.2.2 - Mission Stakeholders - Requirements, Technical Measures, Use Cases - Illustration'::'Stakeholder Concern Name' {
                            doc /* Source XMI: _18_5_2_3880181_1510188711361_846517_64593
                            Stereotype DeriveReqt
                            UML kind: uml:Abstraction */
                        }
                        dependency relationship_47 from OfficialCSRM::'Data'::'02 - CSRM Elements, Examples and Illustrations'::'1 - Stakeholders'::'1.2 Mission Stakeholders'::'1.2.2 - Mission Stakeholders - Requirements, Technical Measures, Use Cases - Illustration'::'Subsystem Requirement Name' to OfficialCSRM::'Data'::'02 - CSRM Elements, Examples and Illustrations'::'1 - Stakeholders'::'1.2 Mission Stakeholders'::'1.2.2 - Mission Stakeholders - Requirements, Technical Measures, Use Cases - Illustration'::'Segment Requirement Name' {
                            doc /* Source XMI: _19_0_2_3880181_1637787984683_139612_56585
                            Stereotype DeriveReqt
                            UML kind: uml:Abstraction */
                        }
                        dependency relationship_48 from OfficialCSRM::'Data'::'02 - CSRM Elements, Examples and Illustrations'::'1 - Stakeholders'::'1.2 Mission Stakeholders'::'1.2.2 - Mission Stakeholders - Requirements, Technical Measures, Use Cases - Illustration'::'Measure of Effectiveness Name' to OfficialCSRM::'Data'::'02 - CSRM Elements, Examples and Illustrations'::'1 - Stakeholders'::'1.2 Mission Stakeholders'::'1.2.2 - Mission Stakeholders - Requirements, Technical Measures, Use Cases - Illustration'::'Mission Requirement Name' {
                            doc /* Source XMI: _19_0_2_3880181_1637860264961_414331_56780
                            Stereotype Refine
                            UML kind: uml:Abstraction */
                        }
                        dependency relationship_49 from OfficialCSRM::'Data'::'02 - CSRM Elements, Examples and Illustrations'::'1 - Stakeholders'::'1.2 Mission Stakeholders'::'1.2.2 - Mission Stakeholders - Requirements, Technical Measures, Use Cases - Illustration'::'Mission Use Case' to OfficialCSRM::'Data'::'02 - CSRM Elements, Examples and Illustrations'::'1 - Stakeholders'::'1.2 Mission Stakeholders'::'1.2.2 - Mission Stakeholders - Requirements, Technical Measures, Use Cases - Illustration'::'Mission Requirement Name' {
                            doc /* Source XMI: _19_0_2_3880181_1637870864266_576029_56857
                            Stereotype Refine
                            UML kind: uml:Abstraction */
                        }
                        dependency relationship_50 from OfficialCSRM::'Data'::'02 - CSRM Elements, Examples and Illustrations'::'1 - Stakeholders'::'1.2 Mission Stakeholders'::'1.2.2 - Mission Stakeholders - Requirements, Technical Measures, Use Cases - Illustration'::'Segment Use Case' to OfficialCSRM::'Data'::'02 - CSRM Elements, Examples and Illustrations'::'1 - Stakeholders'::'1.2 Mission Stakeholders'::'1.2.2 - Mission Stakeholders - Requirements, Technical Measures, Use Cases - Illustration'::'Segment Requirement Name' {
                            doc /* Source XMI: _19_0_2_3880181_1637871012534_770585_56880
                            Stereotype Refine
                            UML kind: uml:Abstraction */
                        }
                        dependency relationship_51 from OfficialCSRM::'Data'::'02 - CSRM Elements, Examples and Illustrations'::'1 - Stakeholders'::'1.2 Mission Stakeholders'::'1.2.2 - Mission Stakeholders - Requirements, Technical Measures, Use Cases - Illustration'::'Subsystem Use Case' to OfficialCSRM::'Data'::'02 - CSRM Elements, Examples and Illustrations'::'1 - Stakeholders'::'1.2 Mission Stakeholders'::'1.2.2 - Mission Stakeholders - Requirements, Technical Measures, Use Cases - Illustration'::'Subsystem Requirement Name' {
                            doc /* Source XMI: _19_0_2_3880181_1642438191124_567898_58431
                            Stereotype Refine
                            UML kind: uml:Abstraction */
                        }
                    }
                    package '1.2.3 - Mission Stakeholders Requirements Relationships - Example' {
                        doc /* Source XMI: _18_5_2_3880181_1508899053594_724029_62629
                        Comment _19_0_2_3880181_1600866306142_386403_63294
                        An example population of mission stakeholders - stakeholder concerns - mission objectives - mission needs - mission constraints -  mission Rqts.
                        Comment _19_0_2_3880181_1637703240911_208051_55600 (Explanation)
                        Mission Stakeholders - Requirements Relationships - Example
                        Comment _19_0_2_3880181_1639412813734_622430_56736 (Explanation)
                        The relationships betweeen elements are captured in the element specifications and containment tree.
                        Those relationships are displayed and maintained in diagrams and tables as shown below
                        UML kind: uml:Package */
                        package '1.2.3.1 - Stakeholders' {
                            doc /* Source XMI: _18_5_2_3880181_1524068060852_562509_66155
                            Comment _19_0_2_3880181_1600979504067_339944_62960
                            Not part of the Foundational CSRM.  An illustration.
                            UML kind: uml:Package */
                            part def 'Chief Scientist' {
                                @OfficialCSRMProfile::'Architecture Structures Profile'::'Stakeholder';
                                doc /* Source XMI: _19_0_3_2b0010b_1619729520402_824154_41743
                                Stereotype Stakeholder
                                UML kind: uml:Class */
                            }
                            part def 'Sponsor' {
                                @OfficialCSRMProfile::'Architecture Structures Profile'::'Stakeholder';
                                doc /* Source XMI: _19_0_3_2b0010b_1619729520696_381223_41819
                                Stereotype Stakeholder
                                UML kind: uml:Class */
                            }
                            part def 'Mission Engineer' {
                                @OfficialCSRMProfile::'Architecture Structures Profile'::'Stakeholder';
                                doc /* Source XMI: _19_0_3_2b0010b_1619729520881_203469_41895
                                Stereotype Stakeholder
                                UML kind: uml:Class */
                            }
                            part def 'Project Manager' {
                                @OfficialCSRMProfile::'Architecture Structures Profile'::'Stakeholder';
                                doc /* Source XMI: _19_0_3_2b0010b_1619729521057_743194_41971
                                Stereotype Stakeholder
                                UML kind: uml:Class */
                            }
                        }
                        package '1.2.3.2 - Stakeholder Concerns' {
                            doc /* Source XMI: _18_5_2_3880181_1524069065989_613667_66735
                            Comment _19_0_2_3880181_1600979895101_208834_62961
                            Not part of the Foundational CSRM.  An illustration.
                            UML kind: uml:Package */
                            part def 'Stakeholder Concerns Group' {
                                @OfficialCSRMProfile::'Concerns and Requirements Profile'::'Group';
                                doc /* Source XMI: _18_5_2_3880181_1524069609514_749983_66794
                                Stereotype Group: Text=This Group provides the prefix and numbering scheme., Id=SC_1
                                UML kind: uml:Class */
                                part def 'Study mission object' {
                                    @OfficialCSRMProfile::'Concerns and Requirements Profile'::'StakeholderConcern';
                                    doc /* Source XMI: _18_5_2_3880181_1524069649422_387347_66800
                                    Stereotype StakeholderConcern: Text=Study mission object shall statement, Id=SC_1.1
                                    UML kind: uml:Class */
                                }
                                part def 'Collect mission data' {
                                    @OfficialCSRMProfile::'Concerns and Requirements Profile'::'StakeholderConcern';
                                    doc /* Source XMI: _19_0_2_3880181_1639411348774_390206_56526
                                    Stereotype StakeholderConcern: Text=, Id=SC_1.2
                                    UML kind: uml:Class */
                                }
                                part def 'Distribute mission data' {
                                    @OfficialCSRMProfile::'Concerns and Requirements Profile'::'StakeholderConcern';
                                    doc /* Source XMI: _19_0_2_3880181_1639411434544_647067_56544
                                    Stereotype StakeholderConcern: Text=, Id=<html><body>SC_1.3</body></html>
                                    UML kind: uml:Class */
                                }
                            }
                            dependency relationship_2 from OfficialCSRM::'Data'::'02 - CSRM Elements, Examples and Illustrations'::'1 - Stakeholders'::'1.2 Mission Stakeholders'::'1.2.3 - Mission Stakeholders Requirements Relationships - Example'::'1.2.3.2 - Stakeholder Concerns'::'Stakeholder Concerns Group'::'Distribute mission data' to OfficialCSRM::'Data'::'02 - CSRM Elements, Examples and Illustrations'::'1 - Stakeholders'::'1.2 Mission Stakeholders'::'1.2.3 - Mission Stakeholders Requirements Relationships - Example'::'1.2.3.1 - Stakeholders'::'Mission Engineer' {
                                @OfficialCSRMProfile::'Architecture Structures Profile'::'ConcernOf';
                                doc /* Source XMI: _19_0_2_3880181_1639411701295_760710_56565
                                Stereotype ConcernOf
                                UML kind: uml:Dependency */
                            }
                            dependency relationship_3 from OfficialCSRM::'Data'::'02 - CSRM Elements, Examples and Illustrations'::'1 - Stakeholders'::'1.2 Mission Stakeholders'::'1.2.3 - Mission Stakeholders Requirements Relationships - Example'::'1.2.3.2 - Stakeholder Concerns'::'Stakeholder Concerns Group'::'Collect mission data' to OfficialCSRM::'Data'::'02 - CSRM Elements, Examples and Illustrations'::'1 - Stakeholders'::'1.2 Mission Stakeholders'::'1.2.3 - Mission Stakeholders Requirements Relationships - Example'::'1.2.3.1 - Stakeholders'::'Mission Engineer' {
                                @OfficialCSRMProfile::'Architecture Structures Profile'::'ConcernOf';
                                doc /* Source XMI: _19_0_2_3880181_1639411754373_192522_56567
                                Stereotype ConcernOf
                                UML kind: uml:Dependency */
                            }
                        }
                        package '1.2.3.3 - Mission Needs' {
                            doc /* Source XMI: _18_5_2_3880181_1524070615713_718348_67149
                            Comment _19_0_2_3880181_1600979910110_310668_62962
                            Not part of the Foundational CSRM.  An illustration.
                            UML kind: uml:Package */
                            part def 'Mission Need Group' {
                                @OfficialCSRMProfile::'Concerns and Requirements Profile'::'Group';
                                doc /* Source XMI: _18_5_2_3880181_1524070653258_965512_67150
                                Stereotype Group: Text=, Id=MN_1
                                UML kind: uml:Class */
                                part def 'Study mission object' {
                                    @OfficialCSRMProfile::'Concerns and Requirements Profile'::'MissionNeed';
                                    doc /* Source XMI: _18_5_2_3880181_1524070679340_326379_67156
                                    Stereotype MissionNeed: Text=Study mission object shall statement, Id=MN_1.1
                                    UML kind: uml:Class */
                                }
                                part def 'Authorization and Funding' {
                                    @OfficialCSRMProfile::'Concerns and Requirements Profile'::'MissionNeed';
                                    doc /* Source XMI: _19_0_2_3880181_1640625926013_852004_57785
                                    Stereotype MissionNeed: Text=, Id=MN_1.2
                                    UML kind: uml:Class */
                                }
                            }
                            dependency relationship_2 from OfficialCSRM::'Data'::'02 - CSRM Elements, Examples and Illustrations'::'1 - Stakeholders'::'1.2 Mission Stakeholders'::'1.2.3 - Mission Stakeholders Requirements Relationships - Example'::'1.2.3.3 - Mission Needs'::'Mission Need Group'::'Study mission object' to OfficialCSRM::'Data'::'02 - CSRM Elements, Examples and Illustrations'::'1 - Stakeholders'::'1.2 Mission Stakeholders'::'1.2.3 - Mission Stakeholders Requirements Relationships - Example'::'1.2.3.1 - Stakeholders'::'Chief Scientist' {
                                @OfficialCSRMProfile::'Architecture Structures Profile'::'ConcernOf';
                                doc /* Source XMI: _19_0_3_2b0010b_1619652216346_104672_34757
                                Stereotype ConcernOf
                                UML kind: uml:Dependency */
                            }
                            dependency relationship_3 from OfficialCSRM::'Data'::'02 - CSRM Elements, Examples and Illustrations'::'1 - Stakeholders'::'1.2 Mission Stakeholders'::'1.2.3 - Mission Stakeholders Requirements Relationships - Example'::'1.2.3.3 - Mission Needs'::'Mission Need Group'::'Study mission object' to OfficialCSRM::'Data'::'02 - CSRM Elements, Examples and Illustrations'::'1 - Stakeholders'::'1.2 Mission Stakeholders'::'1.2.3 - Mission Stakeholders Requirements Relationships - Example'::'1.2.3.1 - Stakeholders'::'Chief Scientist' {
                                doc /* Source XMI: _19_0_2_3880181_1640288988854_814893_57725
                                Stereotype Trace
                                UML kind: uml:Abstraction */
                            }
                            dependency relationship_4 from OfficialCSRM::'Data'::'02 - CSRM Elements, Examples and Illustrations'::'1 - Stakeholders'::'1.2 Mission Stakeholders'::'1.2.3 - Mission Stakeholders Requirements Relationships - Example'::'1.2.3.3 - Mission Needs'::'Mission Need Group'::'Authorization and Funding' to OfficialCSRM::'Data'::'02 - CSRM Elements, Examples and Illustrations'::'1 - Stakeholders'::'1.2 Mission Stakeholders'::'1.2.3 - Mission Stakeholders Requirements Relationships - Example'::'1.2.3.1 - Stakeholders'::'Sponsor' {
                                doc /* Source XMI: _19_0_2_3880181_1640626145154_919566_57825
                                Stereotype Trace
                                UML kind: uml:Abstraction */
                            }
                            dependency relationship_5 from OfficialCSRM::'Data'::'02 - CSRM Elements, Examples and Illustrations'::'1 - Stakeholders'::'1.2 Mission Stakeholders'::'1.2.3 - Mission Stakeholders Requirements Relationships - Example'::'1.2.3.3 - Mission Needs'::'Mission Need Group'::'Authorization and Funding' to OfficialCSRM::'Data'::'02 - CSRM Elements, Examples and Illustrations'::'1 - Stakeholders'::'1.2 Mission Stakeholders'::'1.2.3 - Mission Stakeholders Requirements Relationships - Example'::'1.2.3.1 - Stakeholders'::'Sponsor' {
                                @OfficialCSRMProfile::'Architecture Structures Profile'::'ConcernOf';
                                doc /* Source XMI: _19_0_2_3880181_1640626743622_487420_57840
                                Stereotype ConcernOf
                                UML kind: uml:Dependency */
                            }
                            dependency relationship_6 from OfficialCSRM::'Data'::'02 - CSRM Elements, Examples and Illustrations'::'1 - Stakeholders'::'1.2 Mission Stakeholders'::'1.2.3 - Mission Stakeholders Requirements Relationships - Example'::'1.2.3.3 - Mission Needs'::'Mission Need Group'::'Authorization and Funding' to OfficialCSRM::'Data'::'02 - CSRM Elements, Examples and Illustrations'::'1 - Stakeholders'::'1.2 Mission Stakeholders'::'1.2.3 - Mission Stakeholders Requirements Relationships - Example'::'1.2.3.3 - Mission Needs'::'Mission Need Group'::'Study mission object' {
                                doc /* Source XMI: _19_0_2_3880181_1640627131718_944244_57878
                                Stereotype DeriveReqt
                                UML kind: uml:Abstraction */
                            }
                        }
                        package '1.2.3.4 - Mission Objectives' {
                            doc /* Source XMI: _18_5_2_3880181_1524072075934_585945_67399
                            Comment _19_0_2_3880181_1600979926573_167905_62963
                            Not part of the Foundational CSRM.  An illustration.
                            UML kind: uml:Package */
                            part def 'Mission Objective Group' {
                                @OfficialCSRMProfile::'Concerns and Requirements Profile'::'Group';
                                doc /* Source XMI: _18_5_2_3880181_1524072118667_552136_67400
                                Stereotype Group: Text=This Group provides the prefix and numbering scheme., Id=MO_1
                                UML kind: uml:Class */
                                part def 'Collect mission data' {
                                    @OfficialCSRMProfile::'Concerns and Requirements Profile'::'MissionObjective';
                                    doc /* Source XMI: _18_5_2_3880181_1524072412607_271341_68241
                                    Stereotype MissionObjective: Text=Collect mission data shall statement, Id=MO_1.1
                                    UML kind: uml:Class */
                                }
                                part def 'Distribute mission data' {
                                    @OfficialCSRMProfile::'Concerns and Requirements Profile'::'MissionObjective';
                                    doc /* Source XMI: _18_5_2_3880181_1524072468308_174153_68252
                                    Stereotype MissionObjective: Text=Distribute mission data shall statement, Id=MO_1.2
                                    UML kind: uml:Class */
                                }
                            }
                            dependency relationship_2 from OfficialCSRM::'Data'::'02 - CSRM Elements, Examples and Illustrations'::'1 - Stakeholders'::'1.2 Mission Stakeholders'::'1.2.3 - Mission Stakeholders Requirements Relationships - Example'::'1.2.3.4 - Mission Objectives'::'Mission Objective Group'::'Distribute mission data' to OfficialCSRM::'Data'::'02 - CSRM Elements, Examples and Illustrations'::'1 - Stakeholders'::'1.2 Mission Stakeholders'::'1.2.3 - Mission Stakeholders Requirements Relationships - Example'::'1.2.3.1 - Stakeholders'::'Mission Engineer' {
                                @OfficialCSRMProfile::'Architecture Structures Profile'::'ConcernOf';
                                doc /* Source XMI: _19_0_3_2b0010b_1619652205522_22862_34753
                                Stereotype ConcernOf
                                UML kind: uml:Dependency */
                            }
                            dependency relationship_3 from OfficialCSRM::'Data'::'02 - CSRM Elements, Examples and Illustrations'::'1 - Stakeholders'::'1.2 Mission Stakeholders'::'1.2.3 - Mission Stakeholders Requirements Relationships - Example'::'1.2.3.4 - Mission Objectives'::'Mission Objective Group'::'Collect mission data' to OfficialCSRM::'Data'::'02 - CSRM Elements, Examples and Illustrations'::'1 - Stakeholders'::'1.2 Mission Stakeholders'::'1.2.3 - Mission Stakeholders Requirements Relationships - Example'::'1.2.3.1 - Stakeholders'::'Mission Engineer' {
                                @OfficialCSRMProfile::'Architecture Structures Profile'::'ConcernOf';
                                doc /* Source XMI: _19_0_3_2b0010b_1619652242295_9474_34765
                                Stereotype ConcernOf
                                UML kind: uml:Dependency */
                            }
                            dependency relationship_4 from OfficialCSRM::'Data'::'02 - CSRM Elements, Examples and Illustrations'::'1 - Stakeholders'::'1.2 Mission Stakeholders'::'1.2.3 - Mission Stakeholders Requirements Relationships - Example'::'1.2.3.4 - Mission Objectives'::'Mission Objective Group'::'Distribute mission data' to OfficialCSRM::'Data'::'02 - CSRM Elements, Examples and Illustrations'::'1 - Stakeholders'::'1.2 Mission Stakeholders'::'1.2.3 - Mission Stakeholders Requirements Relationships - Example'::'1.2.3.1 - Stakeholders'::'Mission Engineer' {
                                doc /* Source XMI: _19_0_2_3880181_1640288509571_391711_57544
                                Stereotype Trace
                                UML kind: uml:Abstraction */
                            }
                            dependency relationship_5 from OfficialCSRM::'Data'::'02 - CSRM Elements, Examples and Illustrations'::'1 - Stakeholders'::'1.2 Mission Stakeholders'::'1.2.3 - Mission Stakeholders Requirements Relationships - Example'::'1.2.3.4 - Mission Objectives'::'Mission Objective Group'::'Collect mission data' to OfficialCSRM::'Data'::'02 - CSRM Elements, Examples and Illustrations'::'1 - Stakeholders'::'1.2 Mission Stakeholders'::'1.2.3 - Mission Stakeholders Requirements Relationships - Example'::'1.2.3.1 - Stakeholders'::'Mission Engineer' {
                                doc /* Source XMI: _19_0_2_3880181_1640288617809_724773_57554
                                Stereotype Trace
                                UML kind: uml:Abstraction */
                            }
                            dependency relationship_6 from OfficialCSRM::'Data'::'02 - CSRM Elements, Examples and Illustrations'::'1 - Stakeholders'::'1.2 Mission Stakeholders'::'1.2.3 - Mission Stakeholders Requirements Relationships - Example'::'1.2.3.4 - Mission Objectives'::'Mission Objective Group'::'Distribute mission data' to OfficialCSRM::'Data'::'02 - CSRM Elements, Examples and Illustrations'::'1 - Stakeholders'::'1.2 Mission Stakeholders'::'1.2.3 - Mission Stakeholders Requirements Relationships - Example'::'1.2.3.3 - Mission Needs'::'Mission Need Group'::'Study mission object' {
                                doc /* Source XMI: _19_0_2_3880181_1640631192432_687604_57948
                                Stereotype DeriveReqt
                                UML kind: uml:Abstraction */
                            }
                            dependency relationship_7 from OfficialCSRM::'Data'::'02 - CSRM Elements, Examples and Illustrations'::'1 - Stakeholders'::'1.2 Mission Stakeholders'::'1.2.3 - Mission Stakeholders Requirements Relationships - Example'::'1.2.3.4 - Mission Objectives'::'Mission Objective Group'::'Collect mission data' to OfficialCSRM::'Data'::'02 - CSRM Elements, Examples and Illustrations'::'1 - Stakeholders'::'1.2 Mission Stakeholders'::'1.2.3 - Mission Stakeholders Requirements Relationships - Example'::'1.2.3.3 - Mission Needs'::'Mission Need Group'::'Study mission object' {
                                doc /* Source XMI: _19_0_2_3880181_1640631490848_207165_57977
                                Stereotype DeriveReqt
                                UML kind: uml:Abstraction */
                            }
                        }
                        package '1.2.3.5 - Mission Contraints' {
                            doc /* Source XMI: _18_5_2_3880181_1524072977459_52342_68465
                            Comment _19_0_2_3880181_1600979941504_65627_62964
                            Not part of the Foundational CSRM.  An illustration.
                            UML kind: uml:Package */
                            part def 'Mission Constraints Group' {
                                @OfficialCSRMProfile::'Concerns and Requirements Profile'::'Group';
                                doc /* Source XMI: _18_5_2_3880181_1524073013646_129671_68466
                                Stereotype Group: Text=This Group provides the prefix and numbering scheme., Id=MC_1
                                UML kind: uml:Class */
                                part def 'Carry-out mission for specified time period' {
                                    @OfficialCSRMProfile::'Concerns and Requirements Profile'::'MissionConstraint';
                                    doc /* Source XMI: _18_5_2_3880181_1524073366849_713153_68720
                                    Stereotype MissionConstraint: Text=Shall statement, Id=MC_1.2
                                    UML kind: uml:Class */
                                }
                                part def 'Develop and carry out mission within specified schedule and budget' {
                                    @OfficialCSRMProfile::'Concerns and Requirements Profile'::'MissionConstraint';
                                    doc /* Source XMI: _18_5_2_3880181_1524073272529_511548_68647
                                    Stereotype MissionConstraint: Text=Shall statement, Id=MC_1.1
                                    UML kind: uml:Class */
                                }
                            }
                            dependency relationship_2 from OfficialCSRM::'Data'::'02 - CSRM Elements, Examples and Illustrations'::'1 - Stakeholders'::'1.2 Mission Stakeholders'::'1.2.3 - Mission Stakeholders Requirements Relationships - Example'::'1.2.3.5 - Mission Contraints'::'Mission Constraints Group'::'Develop and carry out mission within specified schedule and budget' to OfficialCSRM::'Data'::'02 - CSRM Elements, Examples and Illustrations'::'1 - Stakeholders'::'1.2 Mission Stakeholders'::'1.2.3 - Mission Stakeholders Requirements Relationships - Example'::'1.2.3.1 - Stakeholders'::'Project Manager' {
                                @OfficialCSRMProfile::'Architecture Structures Profile'::'ConcernOf';
                                doc /* Source XMI: _19_0_3_2b0010b_1619652192285_575828_34749
                                Stereotype ConcernOf
                                UML kind: uml:Dependency */
                            }
                            dependency relationship_3 from OfficialCSRM::'Data'::'02 - CSRM Elements, Examples and Illustrations'::'1 - Stakeholders'::'1.2 Mission Stakeholders'::'1.2.3 - Mission Stakeholders Requirements Relationships - Example'::'1.2.3.5 - Mission Contraints'::'Mission Constraints Group'::'Carry-out mission for specified time period' to OfficialCSRM::'Data'::'02 - CSRM Elements, Examples and Illustrations'::'1 - Stakeholders'::'1.2 Mission Stakeholders'::'1.2.3 - Mission Stakeholders Requirements Relationships - Example'::'1.2.3.1 - Stakeholders'::'Project Manager' {
                                @OfficialCSRMProfile::'Architecture Structures Profile'::'ConcernOf';
                                doc /* Source XMI: _19_0_3_2b0010b_1619652253986_344489_34769
                                Stereotype ConcernOf
                                UML kind: uml:Dependency */
                            }
                            dependency relationship_4 from OfficialCSRM::'Data'::'02 - CSRM Elements, Examples and Illustrations'::'1 - Stakeholders'::'1.2 Mission Stakeholders'::'1.2.3 - Mission Stakeholders Requirements Relationships - Example'::'1.2.3.5 - Mission Contraints'::'Mission Constraints Group'::'Develop and carry out mission within specified schedule and budget' to OfficialCSRM::'Data'::'02 - CSRM Elements, Examples and Illustrations'::'1 - Stakeholders'::'1.2 Mission Stakeholders'::'1.2.3 - Mission Stakeholders Requirements Relationships - Example'::'1.2.3.1 - Stakeholders'::'Project Manager' {
                                doc /* Source XMI: _19_0_2_3880181_1640289475654_26051_57753
                                Stereotype Trace
                                UML kind: uml:Abstraction */
                            }
                            dependency relationship_5 from OfficialCSRM::'Data'::'02 - CSRM Elements, Examples and Illustrations'::'1 - Stakeholders'::'1.2 Mission Stakeholders'::'1.2.3 - Mission Stakeholders Requirements Relationships - Example'::'1.2.3.5 - Mission Contraints'::'Mission Constraints Group'::'Carry-out mission for specified time period' to OfficialCSRM::'Data'::'02 - CSRM Elements, Examples and Illustrations'::'1 - Stakeholders'::'1.2 Mission Stakeholders'::'1.2.3 - Mission Stakeholders Requirements Relationships - Example'::'1.2.3.1 - Stakeholders'::'Project Manager' {
                                doc /* Source XMI: _19_0_2_3880181_1640289490402_134617_57765
                                Stereotype Trace
                                UML kind: uml:Abstraction */
                            }
                        }
                        package '1.2.3.6 - Mission Rqts' {
                            doc /* Source XMI: _18_5_2_3880181_1524074420838_650824_69305
                            Comment _19_0_2_3880181_1600979955418_729543_62965
                            Not part of the Foundational CSRM.  An illustration.
                            UML kind: uml:Package */
                            part def 'Mission Requirement Group' {
                                @OfficialCSRMProfile::'Concerns and Requirements Profile'::'Group';
                                doc /* Source XMI: _18_5_2_3880181_1524074458218_531258_69306
                                Stereotype Group: Text=This Group provides the prefix and numbering scheme., Id=MR_1
                                UML kind: uml:Class */
                                requirement def 'Collect specified quantity' {
                                    @OfficialCSRMProfile::'Concerns and Requirements Profile'::'MissionRequirement';
                                    doc /* Shall statement */
                                    comment /* Source XMI: _18_5_2_3880181_1524075011807_40634_69649
                                    Stereotype MissionRequirement: Text=Shall statement, Id=MR_1.2
                                    UML kind: uml:Class */
                                }
                                requirement def 'Collect specified mission data' {
                                    @OfficialCSRMProfile::'Concerns and Requirements Profile'::'MissionRequirement';
                                    doc /* Shall statement */
                                    comment /* Source XMI: _18_5_2_3880181_1524074899745_808582_69635
                                    Stereotype MissionRequirement: Text=Shall statement, Id=MR_1.1
                                    UML kind: uml:Class */
                                }
                                requirement def 'Collect according to specified conditions' {
                                    @OfficialCSRMProfile::'Concerns and Requirements Profile'::'MissionRequirement';
                                    doc /* Shall statement */
                                    comment /* Source XMI: _18_5_2_3880181_1524074741028_634613_69597
                                    Stereotype MissionRequirement: Text=Shall statement, Id=MR_1.3
                                    UML kind: uml:Class */
                                }
                                requirement def 'Distribute to specified stakeholders' {
                                    @OfficialCSRMProfile::'Concerns and Requirements Profile'::'MissionRequirement';
                                    doc /* Shall statement */
                                    comment /* Source XMI: _18_5_2_3880181_1524075279162_116593_69673
                                    Stereotype MissionRequirement: Text=Shall statement, Id=MR_1.5
                                    UML kind: uml:Class */
                                }
                                requirement def 'Analyze with specified methods' {
                                    @OfficialCSRMProfile::'Concerns and Requirements Profile'::'MissionRequirement';
                                    doc /* Shall statement */
                                    comment /* Source XMI: _18_5_2_3880181_1524075190262_502997_69661
                                    Stereotype MissionRequirement: Text=Shall statement, Id=MR_1.4
                                    UML kind: uml:Class */
                                }
                            }
                            dependency relationship_2 from OfficialCSRM::'Data'::'02 - CSRM Elements, Examples and Illustrations'::'1 - Stakeholders'::'1.2 Mission Stakeholders'::'1.2.3 - Mission Stakeholders Requirements Relationships - Example'::'1.2.3.6 - Mission Rqts'::'Mission Requirement Group'::'Collect according to specified conditions' to OfficialCSRM::'Data'::'02 - CSRM Elements, Examples and Illustrations'::'1 - Stakeholders'::'1.2 Mission Stakeholders'::'1.2.3 - Mission Stakeholders Requirements Relationships - Example'::'1.2.3.4 - Mission Objectives'::'Mission Objective Group'::'Collect mission data' {
                                doc /* Source XMI: _18_5_2_3880181_1524074797444_730230_69605
                                Stereotype DeriveReqt
                                UML kind: uml:Abstraction */
                            }
                            dependency relationship_3 from OfficialCSRM::'Data'::'02 - CSRM Elements, Examples and Illustrations'::'1 - Stakeholders'::'1.2 Mission Stakeholders'::'1.2.3 - Mission Stakeholders Requirements Relationships - Example'::'1.2.3.6 - Mission Rqts'::'Mission Requirement Group'::'Collect specified mission data' to OfficialCSRM::'Data'::'02 - CSRM Elements, Examples and Illustrations'::'1 - Stakeholders'::'1.2 Mission Stakeholders'::'1.2.3 - Mission Stakeholders Requirements Relationships - Example'::'1.2.3.4 - Mission Objectives'::'Mission Objective Group'::'Collect mission data' {
                                doc /* Source XMI: _18_5_2_3880181_1524074939369_222146_69643
                                Stereotype DeriveReqt
                                UML kind: uml:Abstraction */
                            }
                            dependency relationship_4 from OfficialCSRM::'Data'::'02 - CSRM Elements, Examples and Illustrations'::'1 - Stakeholders'::'1.2 Mission Stakeholders'::'1.2.3 - Mission Stakeholders Requirements Relationships - Example'::'1.2.3.6 - Mission Rqts'::'Mission Requirement Group'::'Collect specified quantity' to OfficialCSRM::'Data'::'02 - CSRM Elements, Examples and Illustrations'::'1 - Stakeholders'::'1.2 Mission Stakeholders'::'1.2.3 - Mission Stakeholders Requirements Relationships - Example'::'1.2.3.4 - Mission Objectives'::'Mission Objective Group'::'Collect mission data' {
                                doc /* Source XMI: _18_5_2_3880181_1524075051463_764909_69657
                                Stereotype DeriveReqt
                                UML kind: uml:Abstraction */
                            }
                            dependency relationship_5 from OfficialCSRM::'Data'::'02 - CSRM Elements, Examples and Illustrations'::'1 - Stakeholders'::'1.2 Mission Stakeholders'::'1.2.3 - Mission Stakeholders Requirements Relationships - Example'::'1.2.3.6 - Mission Rqts'::'Mission Requirement Group'::'Analyze with specified methods' to OfficialCSRM::'Data'::'02 - CSRM Elements, Examples and Illustrations'::'1 - Stakeholders'::'1.2 Mission Stakeholders'::'1.2.3 - Mission Stakeholders Requirements Relationships - Example'::'1.2.3.4 - Mission Objectives'::'Mission Objective Group'::'Distribute mission data' {
                                doc /* Source XMI: _18_5_2_3880181_1524075235462_591840_69669
                                Stereotype DeriveReqt
                                UML kind: uml:Abstraction */
                            }
                            dependency relationship_6 from OfficialCSRM::'Data'::'02 - CSRM Elements, Examples and Illustrations'::'1 - Stakeholders'::'1.2 Mission Stakeholders'::'1.2.3 - Mission Stakeholders Requirements Relationships - Example'::'1.2.3.6 - Mission Rqts'::'Mission Requirement Group'::'Distribute to specified stakeholders' to OfficialCSRM::'Data'::'02 - CSRM Elements, Examples and Illustrations'::'1 - Stakeholders'::'1.2 Mission Stakeholders'::'1.2.3 - Mission Stakeholders Requirements Relationships - Example'::'1.2.3.4 - Mission Objectives'::'Mission Objective Group'::'Distribute mission data' {
                                doc /* Source XMI: _18_5_2_3880181_1524075333140_389457_69681
                                Stereotype DeriveReqt
                                UML kind: uml:Abstraction */
                            }
                        }
                    }
                }
            }
            package '2 - Technical Measures' {
                doc /* Source XMI: _19_0_2_3880181_1612801652594_227615_62540
                Comment _19_0_2_3880181_1638718750160_676640_56603 (Explanation)
                Technical Measures - Illustration
                UML kind: uml:Package */
                package '2.2 - Technical Measures - Specifications and Requirements - Illustration' {
                    doc /* Source XMI: _18_5_2_3880181_1523225290730_214038_65576
                    Comment _19_0_2_3880181_1600808302065_211818_63272
                    Not part of the Foundational CSRM.  An illustration of the role of value properties, constraint blocks, and parametrics in assessing technical measures.
                    Comment _19_0_3_2b0010b_1619127788796_857234_621 (HowTo)
                    Double-click on the technical measure table and then click on Add New to add a new technical measure to the containment tree and to the table.
                    The new technical measure element is also added to the technical measure mapping matrix. .
                    Right click the new element in the table then left click Select in Containment Tree to navigate to the new element.
                    Comment _19_0_3_2b0010b_1619128035356_39855_658 (Explanation)
                    Techncial Peformance Measures (TPMs) measure attributes of a system element to determine how well that element is satisfying, or expected to satisfy, a technical requirement
                    Comment _19_0_3_2b0010b_1619128035364_846453_680 (Explanation)
                    Measures of Performance (MOPs) are measures that characterize physical or functional attributes relating to system operation, measured or estimated under specified testing and/or operational environment conditions
                    Comment _19_0_3_2b0010b_1619128035376_95524_702 (Explanation)
                    Measure of Effectivenss (MOEs)  are operational measures of success closely related to the achievement of the mission objective in the intended operational environment under a specified set of conditions
                    Comment _19_0_3_2b0010b_1619128035420_626153_790 (Explanation)
                    Tecnical Measures - Specificationa and Requirements - Illustration
                    Comment _19_0_2_3880181_1641230829129_461941_59184 (Explanation)
                    Key Performance Parameters (KPPs) are measures that are critical and failure to meet threshold performance will result in reevaluation of a technical solution and with the possibility of project termination.
                    UML kind: uml:Package */
                    package 'Technical Measures Requirements ' {
                        doc /* Source XMI: _19_0_2_3880181_1638560756988_480993_56983
                        UML kind: uml:Package */
                    }
                    package 'Technical Measures Specifications' {
                        doc /* Source XMI: _19_0_2_3880181_1638565759533_48887_57703
                        UML kind: uml:Package */
                        package '2.2.4 KPP' {
                            doc /* Source XMI: _19_0_3_2b0010b_1619539835622_561849_27718
                            UML kind: uml:Package */
                            part def 'KppA Specification' {
                                @OfficialCSRMProfile::'Technical Measures Profile'::'kppSpecification';
                                doc /* Source XMI: _19_0_3_2b0010b_1619540582125_186760_28477
                                Stereotype kppSpecification: Id=
                                Comment _19_0_2_3880181_1641227729674_722983_59181
                                Technical measure description
                                UML kind: uml:Class */
                            }
                            dependency relationship_1 from OfficialCSRM::'Data'::'02 - CSRM Elements, Examples and Illustrations'::'2 - Technical Measures'::'2.2 - Technical Measures - Specifications and Requirements - Illustration'::'Technical Measures Specifications'::'2.2.4 KPP'::'KppA Specification' to OfficialCSRM::'Data'::'02 - CSRM Elements, Examples and Illustrations'::'2 - Technical Measures'::'2.2 - Technical Measures - Specifications and Requirements - Illustration'::'Technical Measures Specifications'::'2.2.4 KPP'::'KppA Requirement' {
                                doc /* Source XMI: _19_0_2_3880181_1638644194598_257996_56871
                                Stereotype Refine
                                UML kind: uml:Abstraction */
                            }
                            dependency relationship_2 from OfficialCSRM::'Data'::'02 - CSRM Elements, Examples and Illustrations'::'2 - Technical Measures'::'2.2 - Technical Measures - Specifications and Requirements - Illustration'::'Technical Measures Specifications'::'2.2.4 KPP'::'KppA Specification' to OfficialCSRM::'Data'::'02 - CSRM Elements, Examples and Illustrations'::'2 - Technical Measures'::'2.2 - Technical Measures - Specifications and Requirements - Illustration'::'Technical Measures Specifications'::'2.2.4 KPP'::'KppA Requirement' {
                                doc /* Source XMI: _19_0_2_3880181_1638644589063_413484_56917
                                Stereotype Refine
                                UML kind: uml:Abstraction */
                            }
                            package '2.2.4.1 KPP Specifications' {
                                doc /* Source XMI: _19_0_2_3880181_1640723659128_619169_57627
                                UML kind: uml:Package */
                            }
                            package '2.2.4.2 KPP Requirements' {
                                doc /* Source XMI: _19_0_2_3880181_1640723732253_751997_57629
                                UML kind: uml:Package */
                            }
                            requirement def 'KppA Requirement' {
                                @OfficialCSRMProfile::'Technical Measures Profile'::'kppRequirement';
                                doc /* Shall statement */
                                comment /* Source XMI: _19_0_2_3880181_1638562774721_5098_57540
                                Stereotype kppRequirement: Text=Shall statement, Id=4
                                UML kind: uml:Class */
                            }
                        }
                        package '2.2.3 TPM' {
                            doc /* Source XMI: _18_5_2_3880181_1523225621566_61419_65585
                            Comment _19_0_2_3880181_1600980538624_865614_63244
                            Not part of the Foundational CSRM.  An illustration.
                            UML kind: uml:Package */
                            part def 'TpmA Specification' {
                                @OfficialCSRMProfile::'Technical Measures Profile'::'tpmSpecification';
                                doc /* Source XMI: _19_0_2_3880181_1561574585652_340899_61525
                                Stereotype tpmSpecification
                                Comment _19_0_2_3880181_1641227699938_33202_59180
                                Technical measure description
                                UML kind: uml:Class */
                            }
                            dependency relationship_2 from OfficialCSRM::'Data'::'02 - CSRM Elements, Examples and Illustrations'::'2 - Technical Measures'::'2.2 - Technical Measures - Specifications and Requirements - Illustration'::'Technical Measures Specifications'::'2.2.3 TPM'::'TpmA Specification' to OfficialCSRM::'Data'::'02 - CSRM Elements, Examples and Illustrations'::'2 - Technical Measures'::'2.2 - Technical Measures - Specifications and Requirements - Illustration'::'Technical Measures Specifications'::'2.2.2 MOP'::'MopA Specification' {
                                doc /* Source XMI: _19_0_2_3880181_1638550235504_258957_59305
                                Stereotype Refine
                                UML kind: uml:Abstraction */
                            }
                            dependency relationship_3 from OfficialCSRM::'Data'::'02 - CSRM Elements, Examples and Illustrations'::'2 - Technical Measures'::'2.2 - Technical Measures - Specifications and Requirements - Illustration'::'Technical Measures Specifications'::'2.2.3 TPM'::'TpmA Specification' to OfficialCSRM::'Data'::'02 - CSRM Elements, Examples and Illustrations'::'2 - Technical Measures'::'2.2 - Technical Measures - Specifications and Requirements - Illustration'::'Technical Measures Specifications'::'2.2.3 TPM'::'TpmA Requirement' {
                                doc /* Source XMI: _19_0_2_3880181_1638562733053_748691_57536
                                Stereotype Refine
                                UML kind: uml:Abstraction */
                            }
                            dependency relationship_4 from OfficialCSRM::'Data'::'02 - CSRM Elements, Examples and Illustrations'::'2 - Technical Measures'::'2.2 - Technical Measures - Specifications and Requirements - Illustration'::'Technical Measures Specifications'::'2.2.3 TPM'::'TpmA Specification' to OfficialCSRM::'Data'::'02 - CSRM Elements, Examples and Illustrations'::'2 - Technical Measures'::'2.2 - Technical Measures - Specifications and Requirements - Illustration'::'Technical Measures Specifications'::'2.2.3 TPM'::'TpmA Requirement' {
                                doc /* Source XMI: _19_0_2_3880181_1638565564886_709604_57660
                                Stereotype Refine
                                UML kind: uml:Abstraction */
                            }
                            dependency relationship_5 from OfficialCSRM::'Data'::'02 - CSRM Elements, Examples and Illustrations'::'2 - Technical Measures'::'2.2 - Technical Measures - Specifications and Requirements - Illustration'::'Technical Measures Specifications'::'2.2.3 TPM'::'TpmA Specification' to OfficialCSRM::'Data'::'02 - CSRM Elements, Examples and Illustrations'::'2 - Technical Measures'::'2.2 - Technical Measures - Specifications and Requirements - Illustration'::'Technical Measures Specifications'::'2.2.2 MOP'::'MopA Specification' {
                                doc /* Source XMI: _19_0_2_3880181_1638567844492_871126_58005
                                Stereotype Refine
                                UML kind: uml:Abstraction */
                            }
                            requirement def 'TpmA Requirement' {
                                @OfficialCSRMProfile::'Technical Measures Profile'::'tpmRequirement';
                                doc /* Shall  statement */
                                comment /* Source XMI: _19_0_2_3880181_1638562461658_531078_57460
                                Stereotype tpmRequirement: Text=Shall  statement, Id=3
                                UML kind: uml:Class */
                            }
                            package '2.2.3.1 TPM Specifications' {
                                doc /* Source XMI: _19_0_2_3880181_1640723507580_267590_57625
                                UML kind: uml:Package */
                            }
                            package '2.2.3.2 TPM Requrements' {
                                doc /* Source XMI: _19_0_2_3880181_1640723582955_222870_57626
                                UML kind: uml:Package */
                            }
                        }
                        package '2.2.2 MOP' {
                            doc /* Source XMI: _18_5_2_3880181_1523225596183_47286_65584
                            Comment _19_0_2_3880181_1600980502151_94396_63243
                            Not part of the Foundational CSRM.  An illustration.
                            UML kind: uml:Package */
                            part def 'MopA Specification' {
                                @OfficialCSRMProfile::'Technical Measures Profile'::'mopSpecification';
                                doc /* Source XMI: _18_5_2_3880181_1523236702434_86914_65855
                                Stereotype mopSpecification: Id=
                                Comment _19_0_2_3880181_1641227675032_516187_59179
                                Technical measure description
                                UML kind: uml:Class */
                            }
                            dependency relationship_2 from OfficialCSRM::'Data'::'02 - CSRM Elements, Examples and Illustrations'::'2 - Technical Measures'::'2.2 - Technical Measures - Specifications and Requirements - Illustration'::'Technical Measures Specifications'::'2.2.2 MOP'::'MopA Specification' to OfficialCSRM::'Data'::'02 - CSRM Elements, Examples and Illustrations'::'2 - Technical Measures'::'2.2 - Technical Measures - Specifications and Requirements - Illustration'::'Technical Measures Specifications'::'2.2.1 MOE'::'MoeA Specification' {
                                doc /* Source XMI: _19_0_3_2b0010b_1619540339838_149496_28362
                                Stereotype Refine
                                UML kind: uml:Abstraction */
                            }
                            dependency relationship_3 from OfficialCSRM::'Data'::'02 - CSRM Elements, Examples and Illustrations'::'2 - Technical Measures'::'2.2 - Technical Measures - Specifications and Requirements - Illustration'::'Technical Measures Specifications'::'2.2.2 MOP'::'MopA Specification' to OfficialCSRM::'Data'::'02 - CSRM Elements, Examples and Illustrations'::'2 - Technical Measures'::'2.2 - Technical Measures - Specifications and Requirements - Illustration'::'Technical Measures Specifications'::'2.2.2 MOP'::'MopA Requirement' {
                                doc /* Source XMI: _19_0_2_3880181_1638561240314_727152_57202
                                Stereotype Refine
                                UML kind: uml:Abstraction */
                            }
                            dependency relationship_4 from OfficialCSRM::'Data'::'02 - CSRM Elements, Examples and Illustrations'::'2 - Technical Measures'::'2.2 - Technical Measures - Specifications and Requirements - Illustration'::'Technical Measures Specifications'::'2.2.2 MOP'::'MopA Specification' to OfficialCSRM::'Data'::'02 - CSRM Elements, Examples and Illustrations'::'2 - Technical Measures'::'2.2 - Technical Measures - Specifications and Requirements - Illustration'::'Technical Measures Specifications'::'2.2.2 MOP'::'MopA Requirement' {
                                doc /* Source XMI: _19_0_2_3880181_1638565404777_252246_57652
                                Stereotype Refine
                                UML kind: uml:Abstraction */
                            }
                            dependency relationship_5 from OfficialCSRM::'Data'::'02 - CSRM Elements, Examples and Illustrations'::'2 - Technical Measures'::'2.2 - Technical Measures - Specifications and Requirements - Illustration'::'Technical Measures Specifications'::'2.2.2 MOP'::'MopA Specification' to OfficialCSRM::'Data'::'02 - CSRM Elements, Examples and Illustrations'::'2 - Technical Measures'::'2.2 - Technical Measures - Specifications and Requirements - Illustration'::'Technical Measures Specifications'::'2.2.1 MOE'::'MoeA Specification' {
                                doc /* Source XMI: _19_0_2_3880181_1638567787693_53983_57987
                                Stereotype Refine
                                UML kind: uml:Abstraction */
                            }
                            requirement def 'MopA Requirement' {
                                @OfficialCSRMProfile::'Technical Measures Profile'::'mopRequirement';
                                doc /* Shall statement */
                                comment /* Source XMI: _19_0_2_3880181_1638561121626_86689_57163
                                Stereotype mopRequirement: Text=Shall statement, Id=2
                                UML kind: uml:Class */
                            }
                            package '2.2.2.1 MOP Specifications' {
                                doc /* Source XMI: _19_0_2_3880181_1640723217518_74976_57623
                                UML kind: uml:Package */
                            }
                            package '2.2.2.2 MOP Requirements' {
                                doc /* Source XMI: _19_0_2_3880181_1640723423222_994834_57624
                                UML kind: uml:Package */
                            }
                        }
                        package '2.2.1 MOE' {
                            doc /* Source XMI: _18_5_2_3880181_1523225564595_211889_65583
                            Comment _19_0_2_3880181_1600980478121_965734_63242
                            Not part of the Foundational CSRM.  An illustration.
                            UML kind: uml:Package */
                            part def 'MoeA Specification' {
                                @OfficialCSRMProfile::'Technical Measures Profile'::'moeSpecification';
                                doc /* Source XMI: _19_0_2_3880181_1561574038563_786017_61461
                                Stereotype moeSpecification
                                Comment _19_0_2_3880181_1641227604982_31198_59161
                                Technical measure description
                                UML kind: uml:Class */
                            }
                            dependency relationship_2 from OfficialCSRM::'Data'::'02 - CSRM Elements, Examples and Illustrations'::'2 - Technical Measures'::'2.2 - Technical Measures - Specifications and Requirements - Illustration'::'Technical Measures Specifications'::'2.2.1 MOE'::'MoeA Specification' to OfficialCSRM::'Data'::'02 - CSRM Elements, Examples and Illustrations'::'2 - Technical Measures'::'2.2 - Technical Measures - Specifications and Requirements - Illustration'::'Technical Measures Specifications'::'2.2.1 MOE'::'MoeA Requirement' {
                                doc /* Source XMI: _19_0_2_3880181_1638560219273_463140_56964
                                Stereotype Refine
                                UML kind: uml:Abstraction */
                            }
                            dependency relationship_3 from OfficialCSRM::'Data'::'02 - CSRM Elements, Examples and Illustrations'::'2 - Technical Measures'::'2.2 - Technical Measures - Specifications and Requirements - Illustration'::'Technical Measures Specifications'::'2.2.1 MOE'::'MoeA Specification' to OfficialCSRM::'Data'::'02 - CSRM Elements, Examples and Illustrations'::'2 - Technical Measures'::'2.2 - Technical Measures - Specifications and Requirements - Illustration'::'Technical Measures Specifications'::'2.2.1 MOE'::'MoeA Requirement' {
                                doc /* Source XMI: _19_0_2_3880181_1638560573691_324233_56981
                                Stereotype Refine
                                UML kind: uml:Abstraction */
                            }
                            package '2.2.1.1 MOE Specifications' {
                                doc /* Source XMI: _19_0_2_3880181_1640722257111_644458_57362
                                UML kind: uml:Package */
                            }
                            package '2.2.1.2 MOE Requirements' {
                                doc /* Source XMI: _19_0_2_3880181_1640722457814_61867_57379
                                UML kind: uml:Package */
                            }
                            requirement def 'MoeA Requirement' {
                                @OfficialCSRMProfile::'Technical Measures Profile'::'moeRequirement';
                                doc /* Shall statement */
                                comment /* Source XMI: _19_0_2_3880181_1638559551583_922701_56923
                                Stereotype moeRequirement: Text=Shall statement, Id=1
                                UML kind: uml:Class */
                            }
                        }
                    }
                }
            }
            package '3 - Behaviors' {
                doc /* Source XMI: _19_0_2_3880181_1612801695946_907816_62541
                Comment _19_0_2_3880181_1640191542045_208498_57970 (Explanation)
                Behaviors - Enterprise Level -  Illustration
                Comment _19_0_2_3880181_1640195033955_357727_58209
                A behavior can be:
                Expressed a by text-baed Behavior Description.
                Captured in a Use Case Diagram
                Refined by an Activity Diagram.
                UML kind: uml:Package */
                package '3.3 - Behaviors - Enterprise Level - Illustration' {
                    doc /* Source XMI: _19_0_2_3880181_1655923493064_386968_59369
                    UML kind: uml:Package */
                }
            }
            package '5 - Architecture' {
                doc /* Source XMI: _19_0_2_3880181_1612801728335_93722_62542
                Comment _19_0_2_3880181_1638718136581_435671_56464 (Explanation)
                Enterprise Activities - Example
                UML kind: uml:Package */
                package 'L1_Enterprise Example' {
                    doc /* Source XMI: _19_0_2_3880181_1612808026045_646380_63573
                    UML kind: uml:Package */
                    package 'L1.1_Behaviors Example' {
                        doc /* Source XMI: _19_0_2_3880181_1612808128312_339919_63574
                        UML kind: uml:Package */
                        package 'L1.1-1 Collect and Distribute Mission Data  - Example' {
                            doc /* Source XMI: _18_5_2_3880181_1510846739316_126224_65163
                            Comment _19_0_2_3880181_1601049195385_674309_62598
                            Not part of the Foundational CSRM.  An illustration of use cases and activities: Collect and Distribute Mission Data.
                            Comment _19_0_3_2b0010b_1619477550432_651341_13241 (Explanation)
                            The Collect and Distribute Mission Data behavior can be described by a text based Use Case description, a Use Case diagram, or an Activity diagram - or all three.
                            UML kind: uml:Package */
                            package 'Collect and Distribute Mission Data - Use Case Example' {
                                doc /* Source XMI: _18_5_2_3880181_1510846739316_658349_65164
                                UML kind: uml:Package */
                                package 'CubeSat Mission Enterprise Example' {
                                    doc /* Source XMI: _18_5_2_3880181_1510846739316_598932_65166
                                    UML kind: uml:Model */
                                    use case def 'Collect Mission Data' {
                                        doc /* Source XMI: _18_5_2_3880181_1510846740816_400311_65303
                                        Comment _18_5_2_3880181_1510846741816_984729_65969
                                        Use Case Name: Collect Mission Data
                                        Scope: CubeSat Enterprise
                                        Primary Actor: Chief Scientist
                                        Supporting Actor: Mission Engineer
                                        Stakeholder: Chief Scientist
                                        Preconditions:
                                        Chief Scientist has provided:
                                        • A “list” of objects for study
                                        • The type of mission data to be collected and studied
                                        • The conditions under which the mission data is to be collected
                                        The CubeSat is:
                                        • On-orbit
                                        • Operating normally
                                        • Has an orbit and sensor capable of collecting the mission data under the specified condition
                                        Trigger: Chief Scientist requests collection of mission data
                                        Postconditions: Requested mission data is received by the Ground Segment
                                        UML kind: uml:UseCase */
                                    }
                                    use case def 'Distribute Mission Data' {
                                        doc /* Source XMI: _18_5_2_3880181_1510846740816_640078_65304
                                        Comment _18_5_2_3880181_1510846741816_95762_65970
                                        Use Case Name: Distribute Mission Data
                                        Scope: CubeSat Enterprise
                                        Primary Actor: Chief Scientist
                                        Supporting Actor: Mission Engineer
                                        Stakeholder: Chief Scientist
                                        Preconditions:  Required mission data has been downlinked to the Ground Segment
                                        Trigger: Notification that required mission data has been received
                                        Postconditions: Chief Scientist has received the required mission data and mission data products
                                        UML kind: uml:UseCase */
                                    }
                                    connection def association_2 {
                                        doc /* Source XMI: _18_5_2_3880181_1510846740816_676798_65305
                                        UML end details are in the source map (SysML v2 connector ends have fixed [1..1] multiplicity). */
                                        end end1 : OfficialCSRM::'Data'::'02 - CSRM Elements, Examples and Illustrations'::'5 - Architecture'::'L1_Enterprise Example'::'L1.1_Behaviors Example'::'L1.1-1 Collect and Distribute Mission Data  - Example'::'Collect and Distribute Mission Data - Use Case Example'::'CubeSat Mission Enterprise Example'::'Distribute Mission Data' {
                                            doc /* Source XMI: _18_5_2_3880181_1510846741816_849640_65971
                                            UML end name: (unnamed) */
                                        }
                                        end end2 : OfficialCSRM::'Data'::'02 - CSRM Elements, Examples and Illustrations'::'5 - Architecture'::'L1_Enterprise Example'::'L1.1_Behaviors Example'::'L1.1-1 Collect and Distribute Mission Data  - Example'::'Actors'::'Chief Scientist' {
                                            doc /* Source XMI: _18_5_2_3880181_1510846741816_994106_65972
                                            UML end name: (unnamed) */
                                        }
                                    }
                                    connection def association_3 {
                                        doc /* Source XMI: _18_5_2_3880181_1510846740816_36391_65306
                                        UML end details are in the source map (SysML v2 connector ends have fixed [1..1] multiplicity). */
                                        end end1 : OfficialCSRM::'Data'::'02 - CSRM Elements, Examples and Illustrations'::'5 - Architecture'::'L1_Enterprise Example'::'L1.1_Behaviors Example'::'L1.1-1 Collect and Distribute Mission Data  - Example'::'Collect and Distribute Mission Data - Use Case Example'::'CubeSat Mission Enterprise Example'::'Collect Mission Data' {
                                            doc /* Source XMI: _18_5_2_3880181_1510846741816_795838_65973
                                            UML end name: (unnamed) */
                                        }
                                        end end2 : OfficialCSRM::'Data'::'02 - CSRM Elements, Examples and Illustrations'::'5 - Architecture'::'L1_Enterprise Example'::'L1.1_Behaviors Example'::'L1.1-1 Collect and Distribute Mission Data  - Example'::'Actors'::'Chief Scientist' {
                                            doc /* Source XMI: _18_5_2_3880181_1510846741816_29281_65974
                                            UML end name: (unnamed) */
                                        }
                                    }
                                }
                            }
                            package 'Collect and Distribute Mission Data - Activity Example' {
                                doc /* Source XMI: _18_5_2_3880181_1510846739316_125342_65165
                                UML kind: uml:Package
                                Source-only uml:TimeEvent _18_5_2_3880181_1510846741144_90657_65445: {"type": "uml:TimeEvent", "id": "_18_5_2_3880181_1510846741144_90657_65445"}
                                Source-only uml:TimeExpression _18_5_2_3880181_1510846741816_613825_66012: {"type": "uml:TimeExpression", "id": "_18_5_2_3880181_1510846741816_613825_66012"}
                                Source-only uml:LiteralString _18_5_2_3880181_1510846741847_469106_66156: {"type": "uml:LiteralString", "id": "_18_5_2_3880181_1510846741847_469106_66156", "value": "SpacecraftExecution Time"}
                                Source-only uml:TimeEvent _18_5_2_3880181_1510846741144_821266_65446: {"type": "uml:TimeEvent", "id": "_18_5_2_3880181_1510846741144_821266_65446"}
                                Source-only uml:TimeExpression _18_5_2_3880181_1510846741816_531148_66013: {"type": "uml:TimeExpression", "id": "_18_5_2_3880181_1510846741816_531148_66013"}
                                Source-only uml:LiteralString _18_5_2_3880181_1510846741847_195511_66157: {"type": "uml:LiteralString", "id": "_18_5_2_3880181_1510846741847_195511_66157", "value": "Ground Segement Execution Time"}
                                Source-only uml:TimeEvent _18_5_2_3880181_1510846741410_609000_65593: {"type": "uml:TimeEvent", "id": "_18_5_2_3880181_1510846741410_609000_65593"}
                                Source-only uml:TimeExpression _18_5_2_3880181_1510846741832_672731_66054: {"type": "uml:TimeExpression", "id": "_18_5_2_3880181_1510846741832_672731_66054"}
                                Source-only uml:LiteralString _18_5_2_3880181_1510846741847_596787_66170: {"type": "uml:LiteralString", "id": "_18_5_2_3880181_1510846741847_596787_66170", "value": "Spacecraft Execution Time"}
                                Source-only uml:TimeEvent _18_5_2_3880181_1510846741410_746072_65594: {"type": "uml:TimeEvent", "id": "_18_5_2_3880181_1510846741410_746072_65594"}
                                Source-only uml:TimeExpression _18_5_2_3880181_1510846741832_981865_66055: {"type": "uml:TimeExpression", "id": "_18_5_2_3880181_1510846741832_981865_66055"}
                                Source-only uml:LiteralString _18_5_2_3880181_1510846741847_488298_66171: {"type": "uml:LiteralString", "id": "_18_5_2_3880181_1510846741847_488298_66171", "value": "Ground Segment Execution Time"} */
                                action def 'Generate Mission Data Collection & Space-Ground Comm Schedules' {
                                    doc /* Source XMI: _18_5_2_3880181_1510846739488_323227_65199
                                    UML kind: uml:Activity
                                    Source-only uml:ActivityPartition _18_5_2_3880181_1510846740988_414377_65364: {"type": "uml:ActivityPartition", "id": "_18_5_2_3880181_1510846740988_414377_65364", "visibility": "public", "represents": "_18_0_6_3e4019a_1472151573820_820968_14607"} */
                                    in item parameter_6 {
                                        doc /* Source XMI: _18_5_2_3880181_1510846740816_592685_65311
                                        UML parameter name: Mission Tasking
                                        UML direction: in
                                        UML type: (none) */
                                    }
                                    out item parameter_7 {
                                        doc /* Source XMI: _18_5_2_3880181_1510846740816_566748_65312
                                        UML parameter name: Spacecraft Command Sequence
                                        UML direction: out
                                        UML type: (none) */
                                    }
                                    action node_17 {
                                        doc /* Source XMI: _18_5_2_3880181_1510846740988_295442_65356
                                        UML node kind: uml:ActivityParameterNode
                                        UML node name: argument
                                        UML behavior: (none)
                                        UML parameter: _18_5_2_3880181_1510846740816_592685_65311 */
                                    }
                                    action node_18 {
                                        doc /* Source XMI: _18_5_2_3880181_1510846740988_511718_65357
                                        UML node kind: uml:ActivityParameterNode
                                        UML node name: result
                                        UML behavior: (none)
                                        UML parameter: _18_5_2_3880181_1510846740816_566748_65312 */
                                    }
                                    action node_19 {
                                        doc /* Source XMI: _18_5_2_3880181_1510846740988_472637_65358
                                        UML node kind: uml:CallBehaviorAction
                                        UML node name: (unnamed)
                                        UML behavior: _18_5_2_3880181_1510846739488_674966_65206
                                        UML parameter: (none) */
                                        in item pin_1 {
                                            doc /* Source XMI: _18_5_2_3880181_1510846741816_613142_65983
                                            UML pin name: (unnamed)
                                            UML type: (none) */
                                        }
                                        out item pin_2 {
                                            doc /* Source XMI: _18_5_2_3880181_1510846741816_172932_65982
                                            UML pin name: (unnamed)
                                            UML type: (none) */
                                        }
                                    }
                                    action node_20 {
                                        doc /* Source XMI: _18_5_2_3880181_1510846740988_274308_65359
                                        UML node kind: uml:CallBehaviorAction
                                        UML node name: (unnamed)
                                        UML behavior: _18_5_2_3880181_1510846739488_967886_65207
                                        UML parameter: (none) */
                                        in item pin_1 {
                                            doc /* Source XMI: _18_5_2_3880181_1510846741816_402672_65985
                                            UML pin name: (unnamed)
                                            UML type: (none) */
                                        }
                                        out item pin_2 {
                                            doc /* Source XMI: _18_5_2_3880181_1510846741816_374354_65984
                                            UML pin name: (unnamed)
                                            UML type: (none) */
                                        }
                                    }
                                    action node_21 {
                                        doc /* Source XMI: _18_5_2_3880181_1510846740988_57518_65360
                                        UML node kind: uml:CallBehaviorAction
                                        UML node name: (unnamed)
                                        UML behavior: _18_5_2_3880181_1510846739488_624627_65208
                                        UML parameter: (none) */
                                        in item pin_1 {
                                            doc /* Source XMI: _18_5_2_3880181_1510846741816_82838_65987
                                            UML pin name: (unnamed)
                                            UML type: (none) */
                                        }
                                        in item pin_2 {
                                            doc /* Source XMI: _18_5_2_3880181_1510846741816_450126_65988
                                            UML pin name: (unnamed)
                                            UML type: (none) */
                                        }
                                        out item pin_3 {
                                            doc /* Source XMI: _18_5_2_3880181_1510846741816_941569_65986
                                            UML pin name: (unnamed)
                                            UML type: (none) */
                                        }
                                    }
                                    action node_22 {
                                        doc /* Source XMI: _18_5_2_3880181_1510846740988_991984_65361
                                        UML node kind: uml:CallBehaviorAction
                                        UML node name: (unnamed)
                                        UML behavior: _18_5_2_3880181_1510846739503_398801_65257
                                        UML parameter: (none) */
                                        in item pin_1 {
                                            doc /* Source XMI: _18_5_2_3880181_1510846741816_438726_65990
                                            UML pin name: (unnamed)
                                            UML type: (none) */
                                        }
                                        out item pin_2 {
                                            doc /* Source XMI: _18_5_2_3880181_1510846741816_798339_65989
                                            UML pin name: Mission Data Collection Schedule
                                            UML type: (none) */
                                        }
                                    }
                                    action node_23 {
                                        doc /* Source XMI: _18_5_2_3880181_1510846740988_545171_65362
                                        UML node kind: uml:CallBehaviorAction
                                        UML node name: (unnamed)
                                        UML behavior: _18_5_2_3880181_1510846739503_562203_65258
                                        UML parameter: (none) */
                                        in item pin_1 {
                                            doc /* Source XMI: _18_5_2_3880181_1510846741816_664075_65992
                                            UML pin name: argument
                                            UML type: (none) */
                                        }
                                        out item pin_2 {
                                            doc /* Source XMI: _18_5_2_3880181_1510846741816_646596_65991
                                            UML pin name: Space-Ground Comm Schedule
                                            UML type: (none) */
                                        }
                                    }
                                    action node_24 {
                                        doc /* Source XMI: _18_5_2_3880181_1510846740988_771041_65363
                                        UML node kind: uml:ForkNode
                                        UML node name: (unnamed)
                                        UML behavior: (none)
                                        UML parameter: (none) */
                                    }
                                    dependency call_node_19 from node_19 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Data Collection Schedule';
                                    dependency call_node_20 from node_20 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Space-Ground Comm Schedule';
                                    dependency call_node_21 from node_21 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Spacecraft Command Sequence';
                                    dependency call_node_22 from node_22 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Maintain Mission Data Collection Schedule';
                                    dependency call_node_23 from node_23 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Maintain Space-Ground Comm Schedule';
                                    flow objectFlow_1 from 'node_17' to 'node_19'.pin_1 {
                                        doc /* Source XMI: _18_5_2_3880181_1510846740988_791563_65365
                                        UML ObjectFlow between indexed node or pin endpoints.
                                        Source-only uml:LiteralUnlimitedNatural _18_5_2_3880181_1510846741816_418994_65993: {"type": "uml:LiteralUnlimitedNatural", "id": "_18_5_2_3880181_1510846741816_418994_65993", "value": "1"} */
                                    }
                                    flow objectFlow_2 from 'node_21'.pin_3 to 'node_18' {
                                        doc /* Source XMI: _18_5_2_3880181_1510846740988_116247_65366
                                        UML ObjectFlow between indexed node or pin endpoints.
                                        Source-only uml:LiteralUnlimitedNatural _18_5_2_3880181_1510846741816_882165_65994: {"type": "uml:LiteralUnlimitedNatural", "id": "_18_5_2_3880181_1510846741816_882165_65994", "value": "1"} */
                                    }
                                    flow objectFlow_3 from 'node_19'.pin_2 to 'node_22'.pin_1 {
                                        doc /* Source XMI: _18_5_2_3880181_1510846740988_701316_65367
                                        UML ObjectFlow between indexed node or pin endpoints.
                                        Source-only uml:LiteralUnlimitedNatural _18_5_2_3880181_1510846741816_334069_65995: {"type": "uml:LiteralUnlimitedNatural", "id": "_18_5_2_3880181_1510846741816_334069_65995", "value": "1"} */
                                    }
                                    flow objectFlow_4 from 'node_22'.pin_2 to 'node_24' {
                                        doc /* Source XMI: _18_5_2_3880181_1510846740988_598415_65368
                                        UML ObjectFlow between indexed node or pin endpoints.
                                        Source-only uml:LiteralUnlimitedNatural _18_5_2_3880181_1510846741816_54811_65996: {"type": "uml:LiteralUnlimitedNatural", "id": "_18_5_2_3880181_1510846741816_54811_65996", "value": "1"} */
                                    }
                                    flow objectFlow_5 from 'node_24' to 'node_20'.pin_1 {
                                        doc /* Source XMI: _18_5_2_3880181_1510846740988_884525_65369
                                        UML ObjectFlow between indexed node or pin endpoints.
                                        Source-only uml:LiteralUnlimitedNatural _18_5_2_3880181_1510846741816_687024_65997: {"type": "uml:LiteralUnlimitedNatural", "id": "_18_5_2_3880181_1510846741816_687024_65997", "value": "1"} */
                                    }
                                    flow objectFlow_6 from 'node_24' to 'node_21'.pin_2 {
                                        doc /* Source XMI: _18_5_2_3880181_1510846740988_733830_65370
                                        UML ObjectFlow between indexed node or pin endpoints.
                                        Source-only uml:LiteralUnlimitedNatural _18_5_2_3880181_1510846741816_881889_65998: {"type": "uml:LiteralUnlimitedNatural", "id": "_18_5_2_3880181_1510846741816_881889_65998", "value": "1"} */
                                    }
                                    flow objectFlow_7 from 'node_20'.pin_2 to 'node_23'.pin_1 {
                                        doc /* Source XMI: _18_5_2_3880181_1510846740988_560938_65371
                                        UML ObjectFlow between indexed node or pin endpoints.
                                        Source-only uml:LiteralUnlimitedNatural _18_5_2_3880181_1510846741816_579199_65999: {"type": "uml:LiteralUnlimitedNatural", "id": "_18_5_2_3880181_1510846741816_579199_65999", "value": "1"} */
                                    }
                                    flow objectFlow_8 from 'node_23'.pin_2 to 'node_21'.pin_1 {
                                        doc /* Source XMI: _18_5_2_3880181_1510846740988_337674_65372
                                        UML ObjectFlow between indexed node or pin endpoints.
                                        Source-only uml:LiteralUnlimitedNatural _18_5_2_3880181_1510846741816_273273_66000: {"type": "uml:LiteralUnlimitedNatural", "id": "_18_5_2_3880181_1510846741816_273273_66000", "value": "1"} */
                                    }
                                    part 'property_1' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Data Collection Schedule' {
                                        doc /* Source XMI: _18_5_2_3880181_1510846740988_577221_65351
                                        UML aggregation: composite
                                        UML association: _18_5_2_3880181_1510846739488_100388_65205 */
                                    }
                                    part 'property_2' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Space-Ground Comm Schedule' {
                                        doc /* Source XMI: _18_5_2_3880181_1510846740988_354903_65352
                                        UML aggregation: composite
                                        UML association: _18_5_2_3880181_1510846739488_41611_65209 */
                                    }
                                    part 'property_3' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Spacecraft Command Sequence' {
                                        doc /* Source XMI: _18_5_2_3880181_1510846740988_49907_65353
                                        UML aggregation: composite
                                        UML association: _18_5_2_3880181_1510846739488_577245_65210 */
                                    }
                                    part 'property_4' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Maintain Mission Data Collection Schedule' {
                                        doc /* Source XMI: _18_5_2_3880181_1510846740988_367267_65354
                                        UML aggregation: composite
                                        UML association: _18_5_2_3880181_1510846739503_167238_65259 */
                                    }
                                    part 'property_5' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Maintain Space-Ground Comm Schedule' {
                                        doc /* Source XMI: _18_5_2_3880181_1510846740988_61941_65355
                                        UML aggregation: composite
                                        UML association: _18_5_2_3880181_1510846739503_11868_65260 */
                                    }
                                }
                                action def 'Uplink Spacecraft Command Sequence' {
                                    doc /* Source XMI: _18_5_2_3880181_1510846739488_345163_65200
                                    UML kind: uml:Activity
                                    Source-only uml:ActivityPartition _18_5_2_3880181_1510846741144_263736_65443: {"type": "uml:ActivityPartition", "id": "_18_5_2_3880181_1510846741144_263736_65443", "visibility": "public", "represents": "_18_0_6_3e4019a_1472151573820_820968_14607"}
                                    Source-only uml:ActivityPartition _18_5_2_3880181_1510846741144_559336_65444: {"type": "uml:ActivityPartition", "id": "_18_5_2_3880181_1510846741144_559336_65444", "visibility": "public", "represents": "_18_0_6_3e4019a_1472151573832_997891_14609"} */
                                    in item parameter_7 {
                                        doc /* Source XMI: _18_5_2_3880181_1510846740988_879921_65374
                                        UML parameter name: (unnamed)
                                        UML direction: in
                                        UML type: (none) */
                                    }
                                    out item parameter_8 {
                                        doc /* Source XMI: _18_5_2_3880181_1510846740988_860524_65375
                                        UML parameter name: (unnamed)
                                        UML direction: out
                                        UML type: (none) */
                                    }
                                    action node_23 {
                                        doc /* Source XMI: _18_5_2_3880181_1510846741129_968843_65431
                                        UML node kind: uml:ActivityParameterNode
                                        UML node name: Spacecraft Command Sequence
                                        UML behavior: (none)
                                        UML parameter: (none) */
                                    }
                                    action node_24 {
                                        doc /* Source XMI: _18_5_2_3880181_1510846741129_230779_65432
                                        UML node kind: uml:ActivityParameterNode
                                        UML node name: Spacecraft Command Sequence
                                        UML behavior: (none)
                                        UML parameter: (none) */
                                    }
                                    action node_25 {
                                        doc /* Source XMI: _18_5_2_3880181_1510846741129_201642_65433
                                        UML node kind: uml:CallBehaviorAction
                                        UML node name: (unnamed)
                                        UML behavior: _18_5_2_3880181_1510846739488_914344_65211
                                        UML parameter: (none) */
                                    }
                                    action node_26 {
                                        doc /* Source XMI: _18_5_2_3880181_1510846741129_812831_65434
                                        UML node kind: uml:CallBehaviorAction
                                        UML node name: (unnamed)
                                        UML behavior: _18_5_2_3880181_1510846739503_949433_65212
                                        UML parameter: (none) */
                                        in item pin_1 {
                                            doc /* Source XMI: _18_5_2_3880181_1510846741816_953205_66004
                                            UML pin name: (unnamed)
                                            UML type: (none) */
                                        }
                                    }
                                    action node_27 {
                                        doc /* Source XMI: _18_5_2_3880181_1510846741129_38233_65435
                                        UML node kind: uml:CallBehaviorAction
                                        UML node name: (unnamed)
                                        UML behavior: _18_5_2_3880181_1510846739503_55111_65213
                                        UML parameter: (none) */
                                        in item pin_1 {
                                            doc /* Source XMI: _18_5_2_3880181_1510846741816_429416_66006
                                            UML pin name: (unnamed)
                                            UML type: (none) */
                                        }
                                        out item pin_2 {
                                            doc /* Source XMI: _18_5_2_3880181_1510846741816_457234_66005
                                            UML pin name: (unnamed)
                                            UML type: (none) */
                                        }
                                    }
                                    action node_28 {
                                        doc /* Source XMI: _18_5_2_3880181_1510846741129_551163_65436
                                        UML node kind: uml:CallBehaviorAction
                                        UML node name: (unnamed)
                                        UML behavior: _18_5_2_3880181_1510846739503_133776_65217
                                        UML parameter: (none) */
                                        in item pin_1 {
                                            doc /* Source XMI: _18_5_2_3880181_1510846741816_443878_66008
                                            UML pin name: (unnamed)
                                            UML type: (none) */
                                        }
                                        out item pin_2 {
                                            doc /* Source XMI: _18_5_2_3880181_1510846741816_424408_66007
                                            UML pin name: (unnamed)
                                            UML type: (none) */
                                        }
                                    }
                                    action node_29 {
                                        doc /* Source XMI: _18_5_2_3880181_1510846741129_700840_65437
                                        UML node kind: uml:InitialNode
                                        UML node name: (unnamed)
                                        UML behavior: (none)
                                        UML parameter: (none) */
                                    }
                                    action node_30 {
                                        doc /* Source XMI: _18_5_2_3880181_1510846741129_837259_65438
                                        UML node kind: uml:ForkNode
                                        UML node name: (unnamed)
                                        UML behavior: (none)
                                        UML parameter: (none) */
                                    }
                                    action node_31 {
                                        doc /* Source XMI: _18_5_2_3880181_1510846741129_694981_65439
                                        UML node kind: uml:AcceptEventAction
                                        UML node name: (unnamed)
                                        UML behavior: (none)
                                        UML parameter: (none)
                                        Source-only uml:Trigger _18_5_2_3880181_1510846741816_806970_66009: {"type": "uml:Trigger", "id": "_18_5_2_3880181_1510846741816_806970_66009", "visibility": "public", "event": "_18_5_2_3880181_1510846741144_90657_65445"} */
                                    }
                                    action node_32 {
                                        doc /* Source XMI: _18_5_2_3880181_1510846741144_997054_65440
                                        UML node kind: uml:JoinNode
                                        UML node name: (unnamed)
                                        UML behavior: (none)
                                        UML parameter: (none) */
                                    }
                                    action node_33 {
                                        doc /* Source XMI: _18_5_2_3880181_1510846741144_106467_65441
                                        UML node kind: uml:AcceptEventAction
                                        UML node name: (unnamed)
                                        UML behavior: (none)
                                        UML parameter: (none)
                                        Source-only uml:Trigger _18_5_2_3880181_1510846741816_979679_66010: {"type": "uml:Trigger", "id": "_18_5_2_3880181_1510846741816_979679_66010", "visibility": "public", "event": "_18_5_2_3880181_1510846741144_821266_65446"} */
                                    }
                                    action node_34 {
                                        doc /* Source XMI: _18_5_2_3880181_1510846741144_325795_65442
                                        UML node kind: uml:CallBehaviorAction
                                        UML node name: (unnamed)
                                        UML behavior: _18_5_2_3880181_1510846739503_657722_65261
                                        UML parameter: (none) */
                                        out item pin_1 {
                                            doc /* Source XMI: _18_5_2_3880181_1510846741816_651225_66011
                                            UML pin name: (unnamed)
                                            UML type: (none) */
                                        }
                                    }
                                    dependency call_node_25 from node_25 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Configure Ground Comm Equip for Uplink Transmission';
                                    dependency call_node_26 from node_26 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Configure Spacecraft Comm Equipment for Uplink Reception';
                                    dependency call_node_27 from node_27 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Conduct Uplink of Spacecraft Command Sequence';
                                    dependency call_node_28 from node_28 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Receive Spacecraft Command Sequence';
                                    dependency call_node_34 from node_34 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Retrieve Space-Ground Comm Command Sequence for Uplink';
                                    flow objectFlow_1 from 'node_23' to 'node_27'.pin_1 {
                                        doc /* Source XMI: _18_5_2_3880181_1510846741144_646649_65447
                                        UML ObjectFlow between indexed node or pin endpoints.
                                        Source-only uml:LiteralUnlimitedNatural _18_5_2_3880181_1510846741816_633379_66014: {"type": "uml:LiteralUnlimitedNatural", "id": "_18_5_2_3880181_1510846741816_633379_66014", "value": "1"} */
                                    }
                                    succession controlFlow_2 first 'node_29' then 'node_30' {
                                        doc /* Source XMI: _18_5_2_3880181_1510846741144_573003_65448
                                        UML ControlFlow between indexed node endpoints.
                                        Source-only uml:LiteralUnlimitedNatural _18_5_2_3880181_1510846741816_115253_66015: {"type": "uml:LiteralUnlimitedNatural", "id": "_18_5_2_3880181_1510846741816_115253_66015", "value": "1"} */
                                    }
                                    flow objectFlow_3 from 'node_27'.pin_2 to 'node_28'.pin_1 {
                                        doc /* Source XMI: _18_5_2_3880181_1510846741144_166675_65449
                                        UML ObjectFlow between indexed node or pin endpoints.
                                        Source-only uml:LiteralUnlimitedNatural _18_5_2_3880181_1510846741816_919712_66016: {"type": "uml:LiteralUnlimitedNatural", "id": "_18_5_2_3880181_1510846741816_919712_66016", "value": "1"} */
                                    }
                                    flow objectFlow_4 from 'node_28'.pin_2 to 'node_24' {
                                        doc /* Source XMI: _18_5_2_3880181_1510846741144_118900_65450
                                        UML ObjectFlow between indexed node or pin endpoints.
                                        Source-only uml:LiteralUnlimitedNatural _18_5_2_3880181_1510846741816_360833_66017: {"type": "uml:LiteralUnlimitedNatural", "id": "_18_5_2_3880181_1510846741816_360833_66017", "value": "1"} */
                                    }
                                    succession controlFlow_5 first 'node_30' then 'node_31' {
                                        doc /* Source XMI: _18_5_2_3880181_1510846741144_288647_65451
                                        UML ControlFlow between indexed node endpoints.
                                        Source-only uml:LiteralUnlimitedNatural _18_5_2_3880181_1510846741816_118229_66018: {"type": "uml:LiteralUnlimitedNatural", "id": "_18_5_2_3880181_1510846741816_118229_66018", "value": "1"} */
                                    }
                                    succession controlFlow_6 first 'node_25' then 'node_32' {
                                        doc /* Source XMI: _18_5_2_3880181_1510846741144_359568_65452
                                        UML ControlFlow between indexed node endpoints.
                                        Source-only uml:LiteralUnlimitedNatural _18_5_2_3880181_1510846741816_592270_66019: {"type": "uml:LiteralUnlimitedNatural", "id": "_18_5_2_3880181_1510846741816_592270_66019", "value": "1"} */
                                    }
                                    succession controlFlow_7 first 'node_26' then 'node_32' {
                                        doc /* Source XMI: _18_5_2_3880181_1510846741144_395434_65453
                                        UML ControlFlow between indexed node endpoints.
                                        Source-only uml:LiteralUnlimitedNatural _18_5_2_3880181_1510846741816_701080_66020: {"type": "uml:LiteralUnlimitedNatural", "id": "_18_5_2_3880181_1510846741816_701080_66020", "value": "1"} */
                                    }
                                    succession controlFlow_8 first 'node_32' then 'node_27' {
                                        doc /* Source XMI: _18_5_2_3880181_1510846741144_338825_65454
                                        UML ControlFlow between indexed node endpoints.
                                        Source-only uml:LiteralUnlimitedNatural _18_5_2_3880181_1510846741816_977169_66021: {"type": "uml:LiteralUnlimitedNatural", "id": "_18_5_2_3880181_1510846741816_977169_66021", "value": "1"} */
                                    }
                                    succession controlFlow_9 first 'node_30' then 'node_33' {
                                        doc /* Source XMI: _18_5_2_3880181_1510846741144_49528_65455
                                        UML ControlFlow between indexed node endpoints.
                                        Source-only uml:LiteralUnlimitedNatural _18_5_2_3880181_1510846741816_577612_66022: {"type": "uml:LiteralUnlimitedNatural", "id": "_18_5_2_3880181_1510846741816_577612_66022", "value": "1"} */
                                    }
                                    succession controlFlow_10 first 'node_33' then 'node_25' {
                                        doc /* Source XMI: _18_5_2_3880181_1510846741144_553187_65456
                                        UML ControlFlow between indexed node endpoints.
                                        Source-only uml:LiteralUnlimitedNatural _18_5_2_3880181_1510846741816_822070_66023: {"type": "uml:LiteralUnlimitedNatural", "id": "_18_5_2_3880181_1510846741816_822070_66023", "value": "1"} */
                                    }
                                    succession controlFlow_11 first 'node_31' then 'node_34' {
                                        doc /* Source XMI: _18_5_2_3880181_1510846741144_197226_65457
                                        UML ControlFlow between indexed node endpoints.
                                        Source-only uml:LiteralUnlimitedNatural _18_5_2_3880181_1510846741816_709507_66024: {"type": "uml:LiteralUnlimitedNatural", "id": "_18_5_2_3880181_1510846741816_709507_66024", "value": "1"} */
                                    }
                                    flow objectFlow_12 from 'node_34'.pin_1 to 'node_26'.pin_1 {
                                        doc /* Source XMI: _18_5_2_3880181_1510846741144_363679_65458
                                        UML ObjectFlow between indexed node or pin endpoints.
                                        Source-only uml:LiteralUnlimitedNatural _18_5_2_3880181_1510846741816_942820_66025: {"type": "uml:LiteralUnlimitedNatural", "id": "_18_5_2_3880181_1510846741816_942820_66025", "value": "1"} */
                                    }
                                    part 'property_2' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Configure Ground Comm Equip for Uplink Transmission' {
                                        doc /* Source XMI: _18_5_2_3880181_1510846741129_749591_65426
                                        UML aggregation: composite
                                        UML association: _18_5_2_3880181_1510846739503_157357_65214 */
                                    }
                                    part 'property_3' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Configure Spacecraft Comm Equipment for Uplink Reception' {
                                        doc /* Source XMI: _18_5_2_3880181_1510846741129_748077_65427
                                        UML aggregation: composite
                                        UML association: _18_5_2_3880181_1510846739503_826680_65215 */
                                    }
                                    part 'property_4' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Conduct Uplink of Spacecraft Command Sequence' {
                                        doc /* Source XMI: _18_5_2_3880181_1510846741129_623034_65428
                                        UML aggregation: composite
                                        UML association: _18_5_2_3880181_1510846739503_796713_65216 */
                                    }
                                    part 'property_5' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Receive Spacecraft Command Sequence' {
                                        doc /* Source XMI: _18_5_2_3880181_1510846741129_446046_65429
                                        UML aggregation: composite
                                        UML association: _18_5_2_3880181_1510846739503_758648_65241 */
                                    }
                                    part 'property_6' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Retrieve Space-Ground Comm Command Sequence for Uplink' {
                                        doc /* Source XMI: _18_5_2_3880181_1510846741129_474186_65430
                                        UML aggregation: composite
                                        UML association: _18_5_2_3880181_1510846739503_292467_65262 */
                                    }
                                }
                                action def 'Collect & Pre-Process Mission Data' {
                                    doc /* Source XMI: _18_5_2_3880181_1510846739488_740385_65201
                                    UML kind: uml:Activity
                                    Source-only uml:ActivityPartition _18_5_2_3880181_1510846741269_321861_65513: {"type": "uml:ActivityPartition", "id": "_18_5_2_3880181_1510846741269_321861_65513", "visibility": "public", "represents": "_18_0_6_3e4019a_1472151573832_997891_14609"} */
                                    in item parameter_5 {
                                        doc /* Source XMI: _18_5_2_3880181_1510846741144_309511_65460
                                        UML parameter name: Spacecraft Command Sequence
                                        UML direction: in
                                        UML type: (none) */
                                    }
                                    out item parameter_6 {
                                        doc /* Source XMI: _18_5_2_3880181_1510846741144_617312_65461
                                        UML parameter name: Mission Data
                                        UML direction: out
                                        UML type: (none) */
                                    }
                                    action node_15 {
                                        doc /* Source XMI: _18_5_2_3880181_1510846741269_957198_65505
                                        UML node kind: uml:ActivityParameterNode
                                        UML node name: argument
                                        UML behavior: (none)
                                        UML parameter: _18_5_2_3880181_1510846741144_309511_65460 */
                                    }
                                    action node_16 {
                                        doc /* Source XMI: _18_5_2_3880181_1510846741269_377476_65506
                                        UML node kind: uml:ActivityParameterNode
                                        UML node name: result
                                        UML behavior: (none)
                                        UML parameter: _18_5_2_3880181_1510846741144_617312_65461 */
                                    }
                                    action node_17 {
                                        doc /* Source XMI: _18_5_2_3880181_1510846741269_538915_65507
                                        UML node kind: uml:CallBehaviorAction
                                        UML node name: (unnamed)
                                        UML behavior: _18_5_2_3880181_1510846739503_36597_65218
                                        UML parameter: (none) */
                                        in item pin_1 {
                                            doc /* Source XMI: _18_5_2_3880181_1510846741816_285433_66030
                                            UML pin name: (unnamed)
                                            UML type: (none) */
                                        }
                                        out item pin_2 {
                                            doc /* Source XMI: _18_5_2_3880181_1510846741816_317205_66029
                                            UML pin name: result
                                            UML type: (none) */
                                        }
                                    }
                                    action node_18 {
                                        doc /* Source XMI: _18_5_2_3880181_1510846741269_498424_65508
                                        UML node kind: uml:CallBehaviorAction
                                        UML node name: (unnamed)
                                        UML behavior: _18_5_2_3880181_1510846739503_240597_65219
                                        UML parameter: (none) */
                                        in item pin_1 {
                                            doc /* Source XMI: _18_5_2_3880181_1510846741816_535432_66031
                                            UML pin name: (unnamed)
                                            UML type: (none) */
                                        }
                                    }
                                    action node_19 {
                                        doc /* Source XMI: _18_5_2_3880181_1510846741269_284120_65509
                                        UML node kind: uml:ForkNode
                                        UML node name: (unnamed)
                                        UML behavior: (none)
                                        UML parameter: (none) */
                                    }
                                    action node_20 {
                                        doc /* Source XMI: _18_5_2_3880181_1510846741269_874756_65510
                                        UML node kind: uml:FlowFinalNode
                                        UML node name: (unnamed)
                                        UML behavior: (none)
                                        UML parameter: (none) */
                                    }
                                    action node_21 {
                                        doc /* Source XMI: _18_5_2_3880181_1510846741269_59553_65511
                                        UML node kind: uml:CallBehaviorAction
                                        UML node name: (unnamed)
                                        UML behavior: _18_5_2_3880181_1510846739503_33314_65220
                                        UML parameter: (none) */
                                        in item pin_1 {
                                            doc /* Source XMI: _18_5_2_3880181_1510846741816_451634_66033
                                            UML pin name: argument
                                            UML type: (none) */
                                        }
                                        out item pin_2 {
                                            doc /* Source XMI: _18_5_2_3880181_1510846741816_601945_66032
                                            UML pin name: result
                                            UML type: (none) */
                                        }
                                    }
                                    action node_22 {
                                        doc /* Source XMI: _18_5_2_3880181_1510846741269_811111_65512
                                        UML node kind: uml:CallBehaviorAction
                                        UML node name: (unnamed)
                                        UML behavior: _18_5_2_3880181_1510846739503_278104_65221
                                        UML parameter: (none) */
                                        in item pin_1 {
                                            doc /* Source XMI: _18_5_2_3880181_1510846741816_945944_66035
                                            UML pin name: argument
                                            UML type: (none) */
                                        }
                                        out item pin_2 {
                                            doc /* Source XMI: _18_5_2_3880181_1510846741816_899173_66034
                                            UML pin name: (unnamed)
                                            UML type: (none) */
                                        }
                                    }
                                    dependency call_node_17 from node_17 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Update Mission Data Collection Command Sequence';
                                    dependency call_node_18 from node_18 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Update Space-Ground Comm Command Sequence';
                                    dependency call_node_21 from node_21 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Conduct Mission Data Collection';
                                    dependency call_node_22 from node_22 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Pre-Process Mission Data';
                                    flow objectFlow_1 from 'node_15' to 'node_19' {
                                        doc /* Source XMI: _18_5_2_3880181_1510846741269_901996_65514
                                        UML ObjectFlow between indexed node or pin endpoints.
                                        Source-only uml:LiteralUnlimitedNatural _18_5_2_3880181_1510846741816_401252_66036: {"type": "uml:LiteralUnlimitedNatural", "id": "_18_5_2_3880181_1510846741816_401252_66036", "value": "1"} */
                                    }
                                    flow objectFlow_2 from 'node_19' to 'node_17'.pin_1 {
                                        doc /* Source XMI: _18_5_2_3880181_1510846741269_704908_65515
                                        UML ObjectFlow between indexed node or pin endpoints.
                                        Source-only uml:LiteralUnlimitedNatural _18_5_2_3880181_1510846741816_578647_66037: {"type": "uml:LiteralUnlimitedNatural", "id": "_18_5_2_3880181_1510846741816_578647_66037", "value": "1"} */
                                    }
                                    flow objectFlow_3 from 'node_19' to 'node_18'.pin_1 {
                                        doc /* Source XMI: _18_5_2_3880181_1510846741269_964356_65516
                                        UML ObjectFlow between indexed node or pin endpoints.
                                        Source-only uml:LiteralUnlimitedNatural _18_5_2_3880181_1510846741832_226060_66038: {"type": "uml:LiteralUnlimitedNatural", "id": "_18_5_2_3880181_1510846741832_226060_66038", "value": "1"} */
                                    }
                                    succession controlFlow_4 first 'node_18' then 'node_20' {
                                        doc /* Source XMI: _18_5_2_3880181_1510846741269_40807_65517
                                        UML ControlFlow between indexed node endpoints.
                                        Source-only uml:LiteralUnlimitedNatural _18_5_2_3880181_1510846741832_668190_66039: {"type": "uml:LiteralUnlimitedNatural", "id": "_18_5_2_3880181_1510846741832_668190_66039", "value": "1"} */
                                    }
                                    flow objectFlow_5 from 'node_22'.pin_2 to 'node_16' {
                                        doc /* Source XMI: _18_5_2_3880181_1510846741269_163736_65518
                                        UML ObjectFlow between indexed node or pin endpoints.
                                        Source-only uml:LiteralUnlimitedNatural _18_5_2_3880181_1510846741832_592868_66040: {"type": "uml:LiteralUnlimitedNatural", "id": "_18_5_2_3880181_1510846741832_592868_66040", "value": "1"} */
                                    }
                                    flow objectFlow_6 from 'node_21'.pin_2 to 'node_22'.pin_1 {
                                        doc /* Source XMI: _18_5_2_3880181_1510846741269_396339_65519
                                        UML ObjectFlow between indexed node or pin endpoints.
                                        Source-only uml:LiteralUnlimitedNatural _18_5_2_3880181_1510846741832_459251_66041: {"type": "uml:LiteralUnlimitedNatural", "id": "_18_5_2_3880181_1510846741832_459251_66041", "value": "1"} */
                                    }
                                    flow objectFlow_7 from 'node_17'.pin_2 to 'node_21'.pin_1 {
                                        doc /* Source XMI: _18_5_2_3880181_1510846741269_997410_65520
                                        UML ObjectFlow between indexed node or pin endpoints.
                                        Source-only uml:LiteralUnlimitedNatural _18_5_2_3880181_1510846741832_357297_66042: {"type": "uml:LiteralUnlimitedNatural", "id": "_18_5_2_3880181_1510846741832_357297_66042", "value": "1"} */
                                    }
                                    part 'property_1' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Update Mission Data Collection Command Sequence' {
                                        doc /* Source XMI: _18_5_2_3880181_1510846741269_601834_65501
                                        UML aggregation: composite
                                        UML association: _18_5_2_3880181_1510846739503_951973_65222 */
                                    }
                                    part 'property_2' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Update Space-Ground Comm Command Sequence' {
                                        doc /* Source XMI: _18_5_2_3880181_1510846741269_483806_65502
                                        UML aggregation: composite
                                        UML association: _18_5_2_3880181_1510846739503_629587_65223 */
                                    }
                                    part 'property_3' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Conduct Mission Data Collection' {
                                        doc /* Source XMI: _18_5_2_3880181_1510846741269_673378_65503
                                        UML aggregation: composite
                                        UML association: _18_5_2_3880181_1510846739503_411983_65224 */
                                    }
                                    part 'property_4' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Pre-Process Mission Data' {
                                        doc /* Source XMI: _18_5_2_3880181_1510846741269_567141_65504
                                        UML aggregation: composite
                                        UML association: _18_5_2_3880181_1510846739503_573984_65225 */
                                    }
                                }
                                action def 'Downlink Mission Data' {
                                    doc /* Source XMI: _18_5_2_3880181_1510846739488_856880_65202
                                    UML kind: uml:Activity
                                    Source-only uml:ActivityPartition _18_5_2_3880181_1510846741410_338839_65591: {"type": "uml:ActivityPartition", "id": "_18_5_2_3880181_1510846741410_338839_65591", "visibility": "public", "represents": "_18_0_6_3e4019a_1472151573832_997891_14609"}
                                    Source-only uml:ActivityPartition _18_5_2_3880181_1510846741410_419357_65592: {"type": "uml:ActivityPartition", "id": "_18_5_2_3880181_1510846741410_419357_65592", "visibility": "public", "represents": "_18_0_6_3e4019a_1472151573820_820968_14607"} */
                                    in item parameter_7 {
                                        doc /* Source XMI: _18_5_2_3880181_1510846741269_498801_65522
                                        UML parameter name: Mission Data
                                        UML direction: in
                                        UML type: (none) */
                                    }
                                    out item parameter_8 {
                                        doc /* Source XMI: _18_5_2_3880181_1510846741269_175201_65523
                                        UML parameter name: Mission Data
                                        UML direction: out
                                        UML type: (none) */
                                    }
                                    action node_23 {
                                        doc /* Source XMI: _18_5_2_3880181_1510846741410_179477_65579
                                        UML node kind: uml:ActivityParameterNode
                                        UML node name: Mission Data
                                        UML behavior: (none)
                                        UML parameter: _18_5_2_3880181_1510846741269_498801_65522 */
                                    }
                                    action node_24 {
                                        doc /* Source XMI: _18_5_2_3880181_1510846741410_839312_65580
                                        UML node kind: uml:ActivityParameterNode
                                        UML node name: Mission Data
                                        UML behavior: (none)
                                        UML parameter: _18_5_2_3880181_1510846741269_175201_65523 */
                                    }
                                    action node_25 {
                                        doc /* Source XMI: _18_5_2_3880181_1510846741410_874095_65581
                                        UML node kind: uml:InitialNode
                                        UML node name: (unnamed)
                                        UML behavior: (none)
                                        UML parameter: (none) */
                                    }
                                    action node_26 {
                                        doc /* Source XMI: _18_5_2_3880181_1510846741410_370173_65582
                                        UML node kind: uml:ForkNode
                                        UML node name: (unnamed)
                                        UML behavior: (none)
                                        UML parameter: (none) */
                                    }
                                    action node_27 {
                                        doc /* Source XMI: _18_5_2_3880181_1510846741410_346641_65583
                                        UML node kind: uml:AcceptEventAction
                                        UML node name: (unnamed)
                                        UML behavior: (none)
                                        UML parameter: (none)
                                        Source-only uml:Trigger _18_5_2_3880181_1510846741832_767382_66046: {"type": "uml:Trigger", "id": "_18_5_2_3880181_1510846741832_767382_66046", "visibility": "public", "event": "_18_5_2_3880181_1510846741410_609000_65593"} */
                                    }
                                    action node_28 {
                                        doc /* Source XMI: _18_5_2_3880181_1510846741410_420288_65584
                                        UML node kind: uml:CallBehaviorAction
                                        UML node name: (unnamed)
                                        UML behavior: _18_5_2_3880181_1510846739519_775252_65263
                                        UML parameter: (none) */
                                        out item pin_1 {
                                            doc /* Source XMI: _18_5_2_3880181_1510846741832_680516_66047
                                            UML pin name: (unnamed)
                                            UML type: (none) */
                                        }
                                    }
                                    action node_29 {
                                        doc /* Source XMI: _18_5_2_3880181_1510846741410_841617_65585
                                        UML node kind: uml:CallBehaviorAction
                                        UML node name: (unnamed)
                                        UML behavior: _18_5_2_3880181_1510846739503_223057_65226
                                        UML parameter: (none) */
                                        in item pin_1 {
                                            doc /* Source XMI: _18_5_2_3880181_1510846741832_634812_66048
                                            UML pin name: argument
                                            UML type: (none) */
                                        }
                                    }
                                    action node_30 {
                                        doc /* Source XMI: _18_5_2_3880181_1510846741410_596220_65586
                                        UML node kind: uml:AcceptEventAction
                                        UML node name: (unnamed)
                                        UML behavior: (none)
                                        UML parameter: (none)
                                        Source-only uml:Trigger _18_5_2_3880181_1510846741832_723189_66049: {"type": "uml:Trigger", "id": "_18_5_2_3880181_1510846741832_723189_66049", "visibility": "public", "event": "_18_5_2_3880181_1510846741410_746072_65594"} */
                                    }
                                    action node_31 {
                                        doc /* Source XMI: _18_5_2_3880181_1510846741410_986385_65587
                                        UML node kind: uml:CallBehaviorAction
                                        UML node name: (unnamed)
                                        UML behavior: _18_5_2_3880181_1510846739503_258041_65227
                                        UML parameter: (none) */
                                    }
                                    action node_32 {
                                        doc /* Source XMI: _18_5_2_3880181_1510846741410_341102_65588
                                        UML node kind: uml:JoinNode
                                        UML node name: (unnamed)
                                        UML behavior: (none)
                                        UML parameter: (none) */
                                    }
                                    action node_33 {
                                        doc /* Source XMI: _18_5_2_3880181_1510846741410_795084_65589
                                        UML node kind: uml:CallBehaviorAction
                                        UML node name: (unnamed)
                                        UML behavior: _18_5_2_3880181_1510846739503_292848_65228
                                        UML parameter: (none) */
                                        in item pin_1 {
                                            doc /* Source XMI: _18_5_2_3880181_1510846741832_779583_66051
                                            UML pin name: argument
                                            UML type: (none) */
                                        }
                                        out item pin_2 {
                                            doc /* Source XMI: _18_5_2_3880181_1510846741832_961694_66050
                                            UML pin name: result
                                            UML type: (none) */
                                        }
                                    }
                                    action node_34 {
                                        doc /* Source XMI: _18_5_2_3880181_1510846741410_836881_65590
                                        UML node kind: uml:CallBehaviorAction
                                        UML node name: (unnamed)
                                        UML behavior: _18_5_2_3880181_1510846739503_789400_65232
                                        UML parameter: (none) */
                                        in item pin_1 {
                                            doc /* Source XMI: _18_5_2_3880181_1510846741832_308609_66053
                                            UML pin name: argument
                                            UML type: (none) */
                                        }
                                        out item pin_2 {
                                            doc /* Source XMI: _18_5_2_3880181_1510846741832_955341_66052
                                            UML pin name: result
                                            UML type: (none) */
                                        }
                                    }
                                    dependency call_node_28 from node_28 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Retrieve Space-Ground Comm Command Sequence for Downlink';
                                    dependency call_node_29 from node_29 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Configure Spacecraft Comm Equipment for Downlink Transmission';
                                    dependency call_node_31 from node_31 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Configure Ground Comm Equipment for Downlink Reception';
                                    dependency call_node_33 from node_33 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Conduct Downlink of Mission Data';
                                    dependency call_node_34 from node_34 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Receive Mission Data';
                                    succession controlFlow_1 first 'node_25' then 'node_26' {
                                        doc /* Source XMI: _18_5_2_3880181_1510846741410_831000_65595
                                        UML ControlFlow between indexed node endpoints.
                                        Source-only uml:LiteralUnlimitedNatural _18_5_2_3880181_1510846741832_369028_66056: {"type": "uml:LiteralUnlimitedNatural", "id": "_18_5_2_3880181_1510846741832_369028_66056", "value": "1"} */
                                    }
                                    succession controlFlow_2 first 'node_26' then 'node_27' {
                                        doc /* Source XMI: _18_5_2_3880181_1510846741410_723788_65596
                                        UML ControlFlow between indexed node endpoints.
                                        Source-only uml:LiteralUnlimitedNatural _18_5_2_3880181_1510846741832_15733_66057: {"type": "uml:LiteralUnlimitedNatural", "id": "_18_5_2_3880181_1510846741832_15733_66057", "value": "1"} */
                                    }
                                    succession controlFlow_3 first 'node_27' then 'node_28' {
                                        doc /* Source XMI: _18_5_2_3880181_1510846741410_652430_65597
                                        UML ControlFlow between indexed node endpoints.
                                        Source-only uml:LiteralUnlimitedNatural _18_5_2_3880181_1510846741832_938248_66058: {"type": "uml:LiteralUnlimitedNatural", "id": "_18_5_2_3880181_1510846741832_938248_66058", "value": "1"} */
                                    }
                                    flow objectFlow_4 from 'node_28'.pin_1 to 'node_29'.pin_1 {
                                        doc /* Source XMI: _18_5_2_3880181_1510846741410_562734_65598
                                        UML ObjectFlow between indexed node or pin endpoints.
                                        Source-only uml:LiteralUnlimitedNatural _18_5_2_3880181_1510846741832_199188_66059: {"type": "uml:LiteralUnlimitedNatural", "id": "_18_5_2_3880181_1510846741832_199188_66059", "value": "1"} */
                                    }
                                    succession controlFlow_5 first 'node_26' then 'node_30' {
                                        doc /* Source XMI: _18_5_2_3880181_1510846741410_301318_65599
                                        UML ControlFlow between indexed node endpoints.
                                        Source-only uml:LiteralUnlimitedNatural _18_5_2_3880181_1510846741832_254247_66060: {"type": "uml:LiteralUnlimitedNatural", "id": "_18_5_2_3880181_1510846741832_254247_66060", "value": "1"} */
                                    }
                                    succession controlFlow_6 first 'node_30' then 'node_31' {
                                        doc /* Source XMI: _18_5_2_3880181_1510846741410_264497_65600
                                        UML ControlFlow between indexed node endpoints.
                                        Source-only uml:LiteralUnlimitedNatural _18_5_2_3880181_1510846741832_830840_66061: {"type": "uml:LiteralUnlimitedNatural", "id": "_18_5_2_3880181_1510846741832_830840_66061", "value": "1"} */
                                    }
                                    succession controlFlow_7 first 'node_29' then 'node_32' {
                                        doc /* Source XMI: _18_5_2_3880181_1510846741410_951314_65601
                                        UML ControlFlow between indexed node endpoints.
                                        Source-only uml:LiteralUnlimitedNatural _18_5_2_3880181_1510846741832_989319_66062: {"type": "uml:LiteralUnlimitedNatural", "id": "_18_5_2_3880181_1510846741832_989319_66062", "value": "1"} */
                                    }
                                    succession controlFlow_8 first 'node_31' then 'node_32' {
                                        doc /* Source XMI: _18_5_2_3880181_1510846741410_870142_65602
                                        UML ControlFlow between indexed node endpoints.
                                        Source-only uml:LiteralUnlimitedNatural _18_5_2_3880181_1510846741832_613766_66063: {"type": "uml:LiteralUnlimitedNatural", "id": "_18_5_2_3880181_1510846741832_613766_66063", "value": "1"} */
                                    }
                                    succession controlFlow_9 first 'node_32' then 'node_33' {
                                        doc /* Source XMI: _18_5_2_3880181_1510846741410_242085_65603
                                        UML ControlFlow between indexed node endpoints.
                                        Source-only uml:LiteralUnlimitedNatural _18_5_2_3880181_1510846741832_750135_66064: {"type": "uml:LiteralUnlimitedNatural", "id": "_18_5_2_3880181_1510846741832_750135_66064", "value": "1"} */
                                    }
                                    flow objectFlow_10 from 'node_23' to 'node_33'.pin_1 {
                                        doc /* Source XMI: _18_5_2_3880181_1510846741410_161737_65604
                                        UML ObjectFlow between indexed node or pin endpoints.
                                        Source-only uml:LiteralUnlimitedNatural _18_5_2_3880181_1510846741832_836521_66065: {"type": "uml:LiteralUnlimitedNatural", "id": "_18_5_2_3880181_1510846741832_836521_66065", "value": "1"} */
                                    }
                                    flow objectFlow_11 from 'node_33'.pin_2 to 'node_34'.pin_1 {
                                        doc /* Source XMI: _18_5_2_3880181_1510846741410_678795_65605
                                        UML ObjectFlow between indexed node or pin endpoints.
                                        Source-only uml:LiteralUnlimitedNatural _18_5_2_3880181_1510846741832_252315_66066: {"type": "uml:LiteralUnlimitedNatural", "id": "_18_5_2_3880181_1510846741832_252315_66066", "value": "1"} */
                                    }
                                    flow objectFlow_12 from 'node_34'.pin_2 to 'node_24' {
                                        doc /* Source XMI: _18_5_2_3880181_1510846741410_505891_65606
                                        UML ObjectFlow between indexed node or pin endpoints.
                                        Source-only uml:LiteralUnlimitedNatural _18_5_2_3880181_1510846741832_621057_66067: {"type": "uml:LiteralUnlimitedNatural", "id": "_18_5_2_3880181_1510846741832_621057_66067", "value": "1"} */
                                    }
                                    part 'property_2' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Configure Spacecraft Comm Equipment for Downlink Transmission' {
                                        doc /* Source XMI: _18_5_2_3880181_1510846741410_19089_65574
                                        UML aggregation: composite
                                        UML association: _18_5_2_3880181_1510846739503_628632_65229 */
                                    }
                                    part 'property_3' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Configure Ground Comm Equipment for Downlink Reception' {
                                        doc /* Source XMI: _18_5_2_3880181_1510846741410_60292_65575
                                        UML aggregation: composite
                                        UML association: _18_5_2_3880181_1510846739503_722915_65230 */
                                    }
                                    part 'property_4' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Conduct Downlink of Mission Data' {
                                        doc /* Source XMI: _18_5_2_3880181_1510846741410_210859_65576
                                        UML aggregation: composite
                                        UML association: _18_5_2_3880181_1510846739503_394364_65231 */
                                    }
                                    part 'property_5' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Receive Mission Data' {
                                        doc /* Source XMI: _18_5_2_3880181_1510846741410_263198_65577
                                        UML aggregation: composite
                                        UML association: _18_5_2_3880181_1510846739503_244097_65244 */
                                    }
                                    part 'property_6' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Retrieve Space-Ground Comm Command Sequence for Downlink' {
                                        doc /* Source XMI: _18_5_2_3880181_1510846741410_320792_65578
                                        UML aggregation: composite
                                        UML association: _18_5_2_3880181_1510846739519_228084_65264 */
                                    }
                                }
                                action def 'Distribute Mission Data' {
                                    doc /* Source XMI: _18_5_2_3880181_1510846739488_39328_65203
                                    UML kind: uml:Activity
                                    Source-only uml:ActivityPartition _18_5_2_3880181_1510846741519_743009_65659: {"type": "uml:ActivityPartition", "id": "_18_5_2_3880181_1510846741519_743009_65659", "name": "Ground Segment", "visibility": "public", "represents": "_18_0_6_3e4019a_1472151573820_820968_14607"} */
                                    in item parameter_4 {
                                        doc /* Source XMI: _18_5_2_3880181_1510846741410_700249_65608
                                        UML parameter name: Mission Data
                                        UML direction: in
                                        UML type: (none) */
                                    }
                                    out item parameter_5 {
                                        doc /* Source XMI: _18_5_2_3880181_1510846741410_663041_65609
                                        UML parameter name: Mission Data
                                        UML direction: out
                                        UML type: (none) */
                                    }
                                    out item parameter_6 {
                                        doc /* Source XMI: _18_5_2_3880181_1510846741410_96479_65610
                                        UML parameter name: Mission Data Products
                                        UML direction: out
                                        UML type: (none) */
                                    }
                                    action node_15 {
                                        doc /* Source XMI: _18_5_2_3880181_1510846741519_80944_65652
                                        UML node kind: uml:ActivityParameterNode
                                        UML node name: argument
                                        UML behavior: (none)
                                        UML parameter: _18_5_2_3880181_1510846741410_700249_65608 */
                                    }
                                    action node_16 {
                                        doc /* Source XMI: _18_5_2_3880181_1510846741519_765819_65653
                                        UML node kind: uml:ActivityParameterNode
                                        UML node name: result
                                        UML behavior: (none)
                                        UML parameter: _18_5_2_3880181_1510846741410_663041_65609 */
                                    }
                                    action node_17 {
                                        doc /* Source XMI: _18_5_2_3880181_1510846741519_498830_65654
                                        UML node kind: uml:ActivityParameterNode
                                        UML node name: result
                                        UML behavior: (none)
                                        UML parameter: _18_5_2_3880181_1510846741410_96479_65610 */
                                    }
                                    action node_18 {
                                        doc /* Source XMI: _18_5_2_3880181_1510846741519_519148_65655
                                        UML node kind: uml:CallBehaviorAction
                                        UML node name: (unnamed)
                                        UML behavior: _18_5_2_3880181_1510846739503_300277_65233
                                        UML parameter: (none) */
                                        in item pin_1 {
                                            doc /* Source XMI: _18_5_2_3880181_1510846741832_723579_66072
                                            UML pin name: (unnamed)
                                            UML type: (none) */
                                        }
                                        out item pin_2 {
                                            doc /* Source XMI: _18_5_2_3880181_1510846741832_467334_66071
                                            UML pin name: (unnamed)
                                            UML type: (none) */
                                        }
                                    }
                                    action node_19 {
                                        doc /* Source XMI: _18_5_2_3880181_1510846741519_159566_65656
                                        UML node kind: uml:CallBehaviorAction
                                        UML node name: (unnamed)
                                        UML behavior: _18_5_2_3880181_1510846739503_666860_65234
                                        UML parameter: (none) */
                                        in item pin_1 {
                                            doc /* Source XMI: _18_5_2_3880181_1510846741832_533387_66074
                                            UML pin name: (unnamed)
                                            UML type: (none) */
                                        }
                                        out item pin_2 {
                                            doc /* Source XMI: _18_5_2_3880181_1510846741832_824896_66073
                                            UML pin name: (unnamed)
                                            UML type: (none) */
                                        }
                                    }
                                    action node_20 {
                                        doc /* Source XMI: _18_5_2_3880181_1510846741519_394350_65657
                                        UML node kind: uml:CallBehaviorAction
                                        UML node name: (unnamed)
                                        UML behavior: _18_5_2_3880181_1510846739503_31105_65235
                                        UML parameter: (none) */
                                        in item pin_1 {
                                            doc /* Source XMI: _18_5_2_3880181_1510846741832_896552_66077
                                            UML pin name: (unnamed)
                                            UML type: (none) */
                                        }
                                        in item pin_2 {
                                            doc /* Source XMI: _18_5_2_3880181_1510846741832_567956_66078
                                            UML pin name: (unnamed)
                                            UML type: (none) */
                                        }
                                        out item pin_3 {
                                            doc /* Source XMI: _18_5_2_3880181_1510846741832_752438_66075
                                            UML pin name: (unnamed)
                                            UML type: (none) */
                                        }
                                        out item pin_4 {
                                            doc /* Source XMI: _18_5_2_3880181_1510846741832_748237_66076
                                            UML pin name: (unnamed)
                                            UML type: (none) */
                                        }
                                    }
                                    action node_21 {
                                        doc /* Source XMI: _18_5_2_3880181_1510846741519_72252_65658
                                        UML node kind: uml:ForkNode
                                        UML node name: (unnamed)
                                        UML behavior: (none)
                                        UML parameter: (none) */
                                    }
                                    dependency call_node_18 from node_18 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Post-Process Mission Data';
                                    dependency call_node_19 from node_19 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Data Products';
                                    dependency call_node_20 from node_20 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Distribute Mission Data & Data Products';
                                    flow objectFlow_1 from 'node_18'.pin_2 to 'node_19'.pin_1 {
                                        doc /* Source XMI: _18_5_2_3880181_1510846741519_531938_65660
                                        UML ObjectFlow between indexed node or pin endpoints.
                                        Source-only uml:LiteralUnlimitedNatural _18_5_2_3880181_1510846741832_39418_66079: {"type": "uml:LiteralUnlimitedNatural", "id": "_18_5_2_3880181_1510846741832_39418_66079", "value": "1"} */
                                    }
                                    flow objectFlow_2 from 'node_19'.pin_2 to 'node_20'.pin_1 {
                                        doc /* Source XMI: _18_5_2_3880181_1510846741519_926008_65661
                                        UML ObjectFlow between indexed node or pin endpoints.
                                        Source-only uml:LiteralUnlimitedNatural _18_5_2_3880181_1510846741832_366034_66080: {"type": "uml:LiteralUnlimitedNatural", "id": "_18_5_2_3880181_1510846741832_366034_66080", "value": "1"} */
                                    }
                                    flow objectFlow_3 from 'node_15' to 'node_21' {
                                        doc /* Source XMI: _18_5_2_3880181_1510846741519_63215_65662
                                        UML ObjectFlow between indexed node or pin endpoints.
                                        Source-only uml:LiteralUnlimitedNatural _18_5_2_3880181_1510846741832_938442_66081: {"type": "uml:LiteralUnlimitedNatural", "id": "_18_5_2_3880181_1510846741832_938442_66081", "value": "1"} */
                                    }
                                    flow objectFlow_4 from 'node_21' to 'node_18'.pin_1 {
                                        doc /* Source XMI: _18_5_2_3880181_1510846741519_542379_65663
                                        UML ObjectFlow between indexed node or pin endpoints.
                                        Source-only uml:LiteralUnlimitedNatural _18_5_2_3880181_1510846741832_854301_66082: {"type": "uml:LiteralUnlimitedNatural", "id": "_18_5_2_3880181_1510846741832_854301_66082", "value": "1"} */
                                    }
                                    flow objectFlow_5 from 'node_21' to 'node_20'.pin_2 {
                                        doc /* Source XMI: _18_5_2_3880181_1510846741519_963144_65664
                                        UML ObjectFlow between indexed node or pin endpoints.
                                        Source-only uml:LiteralUnlimitedNatural _18_5_2_3880181_1510846741832_915335_66083: {"type": "uml:LiteralUnlimitedNatural", "id": "_18_5_2_3880181_1510846741832_915335_66083", "value": "1"} */
                                    }
                                    flow objectFlow_6 from 'node_20'.pin_3 to 'node_16' {
                                        doc /* Source XMI: _18_5_2_3880181_1510846741519_503727_65665
                                        UML ObjectFlow between indexed node or pin endpoints.
                                        Source-only uml:LiteralUnlimitedNatural _18_5_2_3880181_1510846741832_335827_66084: {"type": "uml:LiteralUnlimitedNatural", "id": "_18_5_2_3880181_1510846741832_335827_66084", "value": "1"} */
                                    }
                                    flow objectFlow_7 from 'node_20'.pin_4 to 'node_17' {
                                        doc /* Source XMI: _18_5_2_3880181_1510846741519_685314_65666
                                        UML ObjectFlow between indexed node or pin endpoints.
                                        Source-only uml:LiteralUnlimitedNatural _18_5_2_3880181_1510846741832_208498_66085: {"type": "uml:LiteralUnlimitedNatural", "id": "_18_5_2_3880181_1510846741832_208498_66085", "value": "1"} */
                                    }
                                    part 'property_1' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Post-Process Mission Data' {
                                        doc /* Source XMI: _18_5_2_3880181_1510846741519_465324_65649
                                        UML aggregation: composite
                                        UML association: _18_5_2_3880181_1510846739503_102435_65236 */
                                    }
                                    part 'property_2' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Data Products' {
                                        doc /* Source XMI: _18_5_2_3880181_1510846741519_196592_65650
                                        UML aggregation: composite
                                        UML association: _18_5_2_3880181_1510846739503_337823_65237 */
                                    }
                                    part 'property_3' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Distribute Mission Data & Data Products' {
                                        doc /* Source XMI: _18_5_2_3880181_1510846741519_175908_65651
                                        UML aggregation: composite
                                        UML association: _18_5_2_3880181_1510846739503_502516_65238 */
                                    }
                                }
                                connection def association_5 {
                                    doc /* Source XMI: _18_5_2_3880181_1510846739488_735011_65204
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Distribute Mission Data' {
                                        doc /* Source XMI: _18_5_2_3880181_1510846741519_573129_65669
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect and Distribute Mission Data' {
                                        doc /* Source XMI: _18_5_2_3880181_1510846741519_34664_65668
                                        UML end name: (unnamed) */
                                    }
                                }
                                connection def association_6 {
                                    doc /* Source XMI: _18_5_2_3880181_1510846739488_100388_65205
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Data Collection Schedule' {
                                        doc /* Source XMI: _18_5_2_3880181_1510846740988_577221_65351
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Data Collection & Space-Ground Comm Schedules' {
                                        doc /* Source XMI: _18_5_2_3880181_1510846741519_780752_65670
                                        UML end name: (unnamed) */
                                    }
                                }
                                action def 'Generate Mission Data Collection Schedule' {
                                    doc /* Source XMI: _18_5_2_3880181_1510846739488_674966_65206
                                    UML kind: uml:Activity */
                                    in item parameter_0 {
                                        doc /* Source XMI: _18_5_2_3880181_1510846741519_364110_65671
                                        UML parameter name: argument
                                        UML direction: in
                                        UML type: (none) */
                                    }
                                    out item parameter_1 {
                                        doc /* Source XMI: _18_5_2_3880181_1510846741519_893318_65672
                                        UML parameter name: result
                                        UML direction: out
                                        UML type: (none) */
                                    }
                                    action node_2 {
                                        doc /* Source XMI: _18_5_2_3880181_1510846741519_486923_65673
                                        UML node kind: uml:ActivityParameterNode
                                        UML node name: argument
                                        UML behavior: (none)
                                        UML parameter: _18_5_2_3880181_1510846741519_364110_65671 */
                                    }
                                    action node_3 {
                                        doc /* Source XMI: _18_5_2_3880181_1510846741519_721637_65674
                                        UML node kind: uml:ActivityParameterNode
                                        UML node name: result
                                        UML behavior: (none)
                                        UML parameter: _18_5_2_3880181_1510846741519_893318_65672 */
                                    }
                                }
                                action def 'Generate Space-Ground Comm Schedule' {
                                    doc /* Source XMI: _18_5_2_3880181_1510846739488_967886_65207
                                    UML kind: uml:Activity */
                                    in item parameter_0 {
                                        doc /* Source XMI: _18_5_2_3880181_1510846741519_611016_65675
                                        UML parameter name: argument
                                        UML direction: in
                                        UML type: (none) */
                                    }
                                    out item parameter_1 {
                                        doc /* Source XMI: _18_5_2_3880181_1510846741519_407515_65676
                                        UML parameter name: result
                                        UML direction: out
                                        UML type: (none) */
                                    }
                                    action node_2 {
                                        doc /* Source XMI: _18_5_2_3880181_1510846741519_614619_65677
                                        UML node kind: uml:ActivityParameterNode
                                        UML node name: argument
                                        UML behavior: (none)
                                        UML parameter: _18_5_2_3880181_1510846741519_611016_65675 */
                                    }
                                    action node_3 {
                                        doc /* Source XMI: _18_5_2_3880181_1510846741519_985448_65678
                                        UML node kind: uml:ActivityParameterNode
                                        UML node name: result
                                        UML behavior: (none)
                                        UML parameter: _18_5_2_3880181_1510846741519_407515_65676 */
                                    }
                                }
                                action def 'Generate Spacecraft Command Sequence' {
                                    doc /* Source XMI: _18_5_2_3880181_1510846739488_624627_65208
                                    UML kind: uml:Activity */
                                    in item parameter_0 {
                                        doc /* Source XMI: _18_5_2_3880181_1510846741519_836822_65679
                                        UML parameter name: argument
                                        UML direction: in
                                        UML type: (none) */
                                    }
                                    out item parameter_1 {
                                        doc /* Source XMI: _18_5_2_3880181_1510846741519_592923_65680
                                        UML parameter name: result
                                        UML direction: out
                                        UML type: (none) */
                                    }
                                    in item parameter_2 {
                                        doc /* Source XMI: _18_5_2_3880181_1510846741519_430245_65681
                                        UML parameter name: argument
                                        UML direction: in
                                        UML type: (none) */
                                    }
                                    action node_3 {
                                        doc /* Source XMI: _18_5_2_3880181_1510846741519_114931_65682
                                        UML node kind: uml:ActivityParameterNode
                                        UML node name: argument
                                        UML behavior: (none)
                                        UML parameter: _18_5_2_3880181_1510846741519_836822_65679 */
                                    }
                                    action node_4 {
                                        doc /* Source XMI: _18_5_2_3880181_1510846741519_12266_65683
                                        UML node kind: uml:ActivityParameterNode
                                        UML node name: result
                                        UML behavior: (none)
                                        UML parameter: _18_5_2_3880181_1510846741519_592923_65680 */
                                    }
                                    action node_5 {
                                        doc /* Source XMI: _18_5_2_3880181_1510846741519_311236_65684
                                        UML node kind: uml:ActivityParameterNode
                                        UML node name: argument
                                        UML behavior: (none)
                                        UML parameter: _18_5_2_3880181_1510846741519_430245_65681 */
                                    }
                                }
                                connection def association_10 {
                                    doc /* Source XMI: _18_5_2_3880181_1510846739488_41611_65209
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Space-Ground Comm Schedule' {
                                        doc /* Source XMI: _18_5_2_3880181_1510846740988_354903_65352
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Data Collection & Space-Ground Comm Schedules' {
                                        doc /* Source XMI: _18_5_2_3880181_1510846741519_418923_65685
                                        UML end name: (unnamed) */
                                    }
                                }
                                connection def association_11 {
                                    doc /* Source XMI: _18_5_2_3880181_1510846739488_577245_65210
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Spacecraft Command Sequence' {
                                        doc /* Source XMI: _18_5_2_3880181_1510846740988_49907_65353
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Data Collection & Space-Ground Comm Schedules' {
                                        doc /* Source XMI: _18_5_2_3880181_1510846741519_929857_65686
                                        UML end name: (unnamed) */
                                    }
                                }
                                action def 'Configure Ground Comm Equip for Uplink Transmission' {
                                    doc /* Source XMI: _18_5_2_3880181_1510846739488_914344_65211
                                    UML kind: uml:Activity */
                                }
                                action def 'Configure Spacecraft Comm Equipment for Uplink Reception' {
                                    doc /* Source XMI: _18_5_2_3880181_1510846739503_949433_65212
                                    UML kind: uml:Activity */
                                    in item parameter_0 {
                                        doc /* Source XMI: _18_5_2_3880181_1510846741519_833678_65687
                                        UML parameter name: argument
                                        UML direction: in
                                        UML type: (none) */
                                    }
                                    action node_1 {
                                        doc /* Source XMI: _18_5_2_3880181_1510846741519_668592_65688
                                        UML node kind: uml:ActivityParameterNode
                                        UML node name: argument
                                        UML behavior: (none)
                                        UML parameter: _18_5_2_3880181_1510846741519_833678_65687 */
                                    }
                                }
                                action def 'Conduct Uplink of Spacecraft Command Sequence' {
                                    doc /* Source XMI: _18_5_2_3880181_1510846739503_55111_65213
                                    UML kind: uml:Activity */
                                    in item parameter_0 {
                                        doc /* Source XMI: _18_5_2_3880181_1510846741519_542568_65689
                                        UML parameter name: argument
                                        UML direction: in
                                        UML type: (none) */
                                    }
                                    out item parameter_1 {
                                        doc /* Source XMI: _18_5_2_3880181_1510846741519_796611_65690
                                        UML parameter name: result
                                        UML direction: out
                                        UML type: (none) */
                                    }
                                    action node_2 {
                                        doc /* Source XMI: _18_5_2_3880181_1510846741519_847941_65691
                                        UML node kind: uml:ActivityParameterNode
                                        UML node name: argument
                                        UML behavior: (none)
                                        UML parameter: _18_5_2_3880181_1510846741519_542568_65689 */
                                    }
                                    action node_3 {
                                        doc /* Source XMI: _18_5_2_3880181_1510846741519_244279_65692
                                        UML node kind: uml:ActivityParameterNode
                                        UML node name: result
                                        UML behavior: (none)
                                        UML parameter: _18_5_2_3880181_1510846741519_796611_65690 */
                                    }
                                }
                                connection def association_15 {
                                    doc /* Source XMI: _18_5_2_3880181_1510846739503_157357_65214
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Configure Ground Comm Equip for Uplink Transmission' {
                                        doc /* Source XMI: _18_5_2_3880181_1510846741129_749591_65426
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Uplink Spacecraft Command Sequence' {
                                        doc /* Source XMI: _18_5_2_3880181_1510846741519_435634_65693
                                        UML end name: (unnamed) */
                                    }
                                }
                                connection def association_16 {
                                    doc /* Source XMI: _18_5_2_3880181_1510846739503_826680_65215
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Configure Spacecraft Comm Equipment for Uplink Reception' {
                                        doc /* Source XMI: _18_5_2_3880181_1510846741129_748077_65427
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Uplink Spacecraft Command Sequence' {
                                        doc /* Source XMI: _18_5_2_3880181_1510846741519_481253_65694
                                        UML end name: (unnamed) */
                                    }
                                }
                                connection def association_17 {
                                    doc /* Source XMI: _18_5_2_3880181_1510846739503_796713_65216
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Conduct Uplink of Spacecraft Command Sequence' {
                                        doc /* Source XMI: _18_5_2_3880181_1510846741129_623034_65428
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Uplink Spacecraft Command Sequence' {
                                        doc /* Source XMI: _18_5_2_3880181_1510846741519_556432_65695
                                        UML end name: (unnamed) */
                                    }
                                }
                                action def 'Receive Spacecraft Command Sequence' {
                                    doc /* Source XMI: _18_5_2_3880181_1510846739503_133776_65217
                                    UML kind: uml:Activity */
                                    in item parameter_0 {
                                        doc /* Source XMI: _18_5_2_3880181_1510846741519_265736_65696
                                        UML parameter name: argument
                                        UML direction: in
                                        UML type: (none) */
                                    }
                                    out item parameter_1 {
                                        doc /* Source XMI: _18_5_2_3880181_1510846741519_463753_65697
                                        UML parameter name: result
                                        UML direction: out
                                        UML type: (none) */
                                    }
                                    action node_2 {
                                        doc /* Source XMI: _18_5_2_3880181_1510846741519_612708_65698
                                        UML node kind: uml:ActivityParameterNode
                                        UML node name: argument
                                        UML behavior: (none)
                                        UML parameter: _18_5_2_3880181_1510846741519_265736_65696 */
                                    }
                                    action node_3 {
                                        doc /* Source XMI: _18_5_2_3880181_1510846741519_498440_65699
                                        UML node kind: uml:ActivityParameterNode
                                        UML node name: result
                                        UML behavior: (none)
                                        UML parameter: _18_5_2_3880181_1510846741519_463753_65697 */
                                    }
                                }
                                action def 'Update Mission Data Collection Command Sequence' {
                                    doc /* Source XMI: _18_5_2_3880181_1510846739503_36597_65218
                                    UML kind: uml:Activity */
                                    in item parameter_0 {
                                        doc /* Source XMI: _18_5_2_3880181_1510846741519_112437_65700
                                        UML parameter name: argument
                                        UML direction: in
                                        UML type: (none) */
                                    }
                                    out item parameter_1 {
                                        doc /* Source XMI: _18_5_2_3880181_1510846741519_271277_65701
                                        UML parameter name: result
                                        UML direction: out
                                        UML type: (none) */
                                    }
                                    action node_2 {
                                        doc /* Source XMI: _18_5_2_3880181_1510846741519_64943_65702
                                        UML node kind: uml:ActivityParameterNode
                                        UML node name: argument
                                        UML behavior: (none)
                                        UML parameter: _18_5_2_3880181_1510846741519_112437_65700 */
                                    }
                                    action node_3 {
                                        doc /* Source XMI: _18_5_2_3880181_1510846741519_448380_65703
                                        UML node kind: uml:ActivityParameterNode
                                        UML node name: result
                                        UML behavior: (none)
                                        UML parameter: _18_5_2_3880181_1510846741519_271277_65701 */
                                    }
                                }
                                action def 'Update Space-Ground Comm Command Sequence' {
                                    doc /* Source XMI: _18_5_2_3880181_1510846739503_240597_65219
                                    UML kind: uml:Activity */
                                    in item parameter_0 {
                                        doc /* Source XMI: _18_5_2_3880181_1510846741519_79123_65704
                                        UML parameter name: argument
                                        UML direction: in
                                        UML type: (none) */
                                    }
                                    action node_1 {
                                        doc /* Source XMI: _18_5_2_3880181_1510846741519_468136_65705
                                        UML node kind: uml:ActivityParameterNode
                                        UML node name: argument
                                        UML behavior: (none)
                                        UML parameter: _18_5_2_3880181_1510846741519_79123_65704 */
                                    }
                                }
                                action def 'Conduct Mission Data Collection' {
                                    doc /* Source XMI: _18_5_2_3880181_1510846739503_33314_65220
                                    UML kind: uml:Activity */
                                    out item parameter_0 {
                                        doc /* Source XMI: _18_5_2_3880181_1510846741519_630487_65706
                                        UML parameter name: result
                                        UML direction: out
                                        UML type: (none) */
                                    }
                                    in item parameter_1 {
                                        doc /* Source XMI: _18_5_2_3880181_1510846741519_26148_65707
                                        UML parameter name: argument
                                        UML direction: in
                                        UML type: (none) */
                                    }
                                    action node_2 {
                                        doc /* Source XMI: _18_5_2_3880181_1510846741519_157914_65708
                                        UML node kind: uml:ActivityParameterNode
                                        UML node name: result
                                        UML behavior: (none)
                                        UML parameter: _18_5_2_3880181_1510846741519_630487_65706 */
                                    }
                                    action node_3 {
                                        doc /* Source XMI: _18_5_2_3880181_1510846741519_662112_65709
                                        UML node kind: uml:ActivityParameterNode
                                        UML node name: argument
                                        UML behavior: (none)
                                        UML parameter: _18_5_2_3880181_1510846741519_26148_65707 */
                                    }
                                }
                                action def 'Pre-Process Mission Data' {
                                    doc /* Source XMI: _18_5_2_3880181_1510846739503_278104_65221
                                    UML kind: uml:Activity */
                                    out item parameter_0 {
                                        doc /* Source XMI: _18_5_2_3880181_1510846741519_202355_65710
                                        UML parameter name: Mission Data
                                        UML direction: out
                                        UML type: (none) */
                                    }
                                    in item parameter_1 {
                                        doc /* Source XMI: _18_5_2_3880181_1510846741519_216253_65711
                                        UML parameter name: argument
                                        UML direction: in
                                        UML type: (none) */
                                    }
                                    action node_2 {
                                        doc /* Source XMI: _18_5_2_3880181_1510846741519_709227_65712
                                        UML node kind: uml:ActivityParameterNode
                                        UML node name: result
                                        UML behavior: (none)
                                        UML parameter: _18_5_2_3880181_1510846741519_202355_65710 */
                                    }
                                    action node_3 {
                                        doc /* Source XMI: _18_5_2_3880181_1510846741519_129508_65713
                                        UML node kind: uml:ActivityParameterNode
                                        UML node name: argument
                                        UML behavior: (none)
                                        UML parameter: _18_5_2_3880181_1510846741519_216253_65711 */
                                    }
                                }
                                connection def association_23 {
                                    doc /* Source XMI: _18_5_2_3880181_1510846739503_951973_65222
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Update Mission Data Collection Command Sequence' {
                                        doc /* Source XMI: _18_5_2_3880181_1510846741269_601834_65501
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect & Pre-Process Mission Data' {
                                        doc /* Source XMI: _18_5_2_3880181_1510846741519_307430_65714
                                        UML end name: (unnamed) */
                                    }
                                }
                                connection def association_24 {
                                    doc /* Source XMI: _18_5_2_3880181_1510846739503_629587_65223
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Update Space-Ground Comm Command Sequence' {
                                        doc /* Source XMI: _18_5_2_3880181_1510846741269_483806_65502
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect & Pre-Process Mission Data' {
                                        doc /* Source XMI: _18_5_2_3880181_1510846741519_518897_65715
                                        UML end name: (unnamed) */
                                    }
                                }
                                connection def association_25 {
                                    doc /* Source XMI: _18_5_2_3880181_1510846739503_411983_65224
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Conduct Mission Data Collection' {
                                        doc /* Source XMI: _18_5_2_3880181_1510846741269_673378_65503
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect & Pre-Process Mission Data' {
                                        doc /* Source XMI: _18_5_2_3880181_1510846741519_282987_65716
                                        UML end name: (unnamed) */
                                    }
                                }
                                connection def association_26 {
                                    doc /* Source XMI: _18_5_2_3880181_1510846739503_573984_65225
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Pre-Process Mission Data' {
                                        doc /* Source XMI: _18_5_2_3880181_1510846741269_567141_65504
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect & Pre-Process Mission Data' {
                                        doc /* Source XMI: _18_5_2_3880181_1510846741519_35390_65717
                                        UML end name: (unnamed) */
                                    }
                                }
                                action def 'Configure Spacecraft Comm Equipment for Downlink Transmission' {
                                    doc /* Source XMI: _18_5_2_3880181_1510846739503_223057_65226
                                    UML kind: uml:Activity */
                                    in item parameter_0 {
                                        doc /* Source XMI: _18_5_2_3880181_1510846741519_241579_65718
                                        UML parameter name: argument
                                        UML direction: in
                                        UML type: (none) */
                                    }
                                    action node_1 {
                                        doc /* Source XMI: _18_5_2_3880181_1510846741519_714975_65719
                                        UML node kind: uml:ActivityParameterNode
                                        UML node name: argument
                                        UML behavior: (none)
                                        UML parameter: _18_5_2_3880181_1510846741519_241579_65718 */
                                    }
                                }
                                action def 'Configure Ground Comm Equipment for Downlink Reception' {
                                    doc /* Source XMI: _18_5_2_3880181_1510846739503_258041_65227
                                    UML kind: uml:Activity */
                                }
                                action def 'Conduct Downlink of Mission Data' {
                                    doc /* Source XMI: _18_5_2_3880181_1510846739503_292848_65228
                                    UML kind: uml:Activity */
                                    in item parameter_0 {
                                        doc /* Source XMI: _18_5_2_3880181_1510846741519_524496_65720
                                        UML parameter name: argument
                                        UML direction: in
                                        UML type: (none) */
                                    }
                                    out item parameter_1 {
                                        doc /* Source XMI: _18_5_2_3880181_1510846741519_263984_65721
                                        UML parameter name: result
                                        UML direction: out
                                        UML type: (none) */
                                    }
                                    action node_2 {
                                        doc /* Source XMI: _18_5_2_3880181_1510846741519_245245_65722
                                        UML node kind: uml:ActivityParameterNode
                                        UML node name: argument
                                        UML behavior: (none)
                                        UML parameter: _18_5_2_3880181_1510846741519_524496_65720 */
                                    }
                                    action node_3 {
                                        doc /* Source XMI: _18_5_2_3880181_1510846741519_516986_65723
                                        UML node kind: uml:ActivityParameterNode
                                        UML node name: result
                                        UML behavior: (none)
                                        UML parameter: _18_5_2_3880181_1510846741519_263984_65721 */
                                    }
                                }
                                connection def association_30 {
                                    doc /* Source XMI: _18_5_2_3880181_1510846739503_628632_65229
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Configure Spacecraft Comm Equipment for Downlink Transmission' {
                                        doc /* Source XMI: _18_5_2_3880181_1510846741410_19089_65574
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Downlink Mission Data' {
                                        doc /* Source XMI: _18_5_2_3880181_1510846741519_53419_65724
                                        UML end name: (unnamed) */
                                    }
                                }
                                connection def association_31 {
                                    doc /* Source XMI: _18_5_2_3880181_1510846739503_722915_65230
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Configure Ground Comm Equipment for Downlink Reception' {
                                        doc /* Source XMI: _18_5_2_3880181_1510846741410_60292_65575
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Downlink Mission Data' {
                                        doc /* Source XMI: _18_5_2_3880181_1510846741519_600444_65725
                                        UML end name: (unnamed) */
                                    }
                                }
                                connection def association_32 {
                                    doc /* Source XMI: _18_5_2_3880181_1510846739503_394364_65231
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Conduct Downlink of Mission Data' {
                                        doc /* Source XMI: _18_5_2_3880181_1510846741410_210859_65576
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Downlink Mission Data' {
                                        doc /* Source XMI: _18_5_2_3880181_1510846741519_128008_65726
                                        UML end name: (unnamed) */
                                    }
                                }
                                action def 'Receive Mission Data' {
                                    doc /* Source XMI: _18_5_2_3880181_1510846739503_789400_65232
                                    UML kind: uml:Activity */
                                    in item parameter_0 {
                                        doc /* Source XMI: _18_5_2_3880181_1510846741519_699167_65727
                                        UML parameter name: argument
                                        UML direction: in
                                        UML type: (none) */
                                    }
                                    out item parameter_1 {
                                        doc /* Source XMI: _18_5_2_3880181_1510846741519_439693_65728
                                        UML parameter name: result
                                        UML direction: out
                                        UML type: (none) */
                                    }
                                    action node_2 {
                                        doc /* Source XMI: _18_5_2_3880181_1510846741519_217180_65729
                                        UML node kind: uml:ActivityParameterNode
                                        UML node name: argument
                                        UML behavior: (none)
                                        UML parameter: _18_5_2_3880181_1510846741519_699167_65727 */
                                    }
                                    action node_3 {
                                        doc /* Source XMI: _18_5_2_3880181_1510846741519_501549_65730
                                        UML node kind: uml:ActivityParameterNode
                                        UML node name: result
                                        UML behavior: (none)
                                        UML parameter: _18_5_2_3880181_1510846741519_439693_65728 */
                                    }
                                }
                                action def 'Post-Process Mission Data' {
                                    doc /* Source XMI: _18_5_2_3880181_1510846739503_300277_65233
                                    UML kind: uml:Activity */
                                    in item parameter_0 {
                                        doc /* Source XMI: _18_5_2_3880181_1510846741519_652657_65731
                                        UML parameter name: argument
                                        UML direction: in
                                        UML type: (none) */
                                    }
                                    out item parameter_1 {
                                        doc /* Source XMI: _18_5_2_3880181_1510846741519_916775_65732
                                        UML parameter name: result
                                        UML direction: out
                                        UML type: (none) */
                                    }
                                    action node_2 {
                                        doc /* Source XMI: _18_5_2_3880181_1510846741519_161039_65733
                                        UML node kind: uml:ActivityParameterNode
                                        UML node name: argument
                                        UML behavior: (none)
                                        UML parameter: _18_5_2_3880181_1510846741519_652657_65731 */
                                    }
                                    action node_3 {
                                        doc /* Source XMI: _18_5_2_3880181_1510846741535_312727_65734
                                        UML node kind: uml:ActivityParameterNode
                                        UML node name: result
                                        UML behavior: (none)
                                        UML parameter: _18_5_2_3880181_1510846741519_916775_65732 */
                                    }
                                }
                                action def 'Generate Mission Data Products' {
                                    doc /* Source XMI: _18_5_2_3880181_1510846739503_666860_65234
                                    UML kind: uml:Activity */
                                    in item parameter_0 {
                                        doc /* Source XMI: _18_5_2_3880181_1510846741535_695331_65735
                                        UML parameter name: argument
                                        UML direction: in
                                        UML type: (none) */
                                    }
                                    out item parameter_1 {
                                        doc /* Source XMI: _18_5_2_3880181_1510846741535_270480_65736
                                        UML parameter name: result
                                        UML direction: out
                                        UML type: (none) */
                                    }
                                    action node_2 {
                                        doc /* Source XMI: _18_5_2_3880181_1510846741535_812087_65737
                                        UML node kind: uml:ActivityParameterNode
                                        UML node name: argument
                                        UML behavior: (none)
                                        UML parameter: _18_5_2_3880181_1510846741535_695331_65735 */
                                    }
                                    action node_3 {
                                        doc /* Source XMI: _18_5_2_3880181_1510846741535_681888_65738
                                        UML node kind: uml:ActivityParameterNode
                                        UML node name: result
                                        UML behavior: (none)
                                        UML parameter: _18_5_2_3880181_1510846741535_270480_65736 */
                                    }
                                }
                                action def 'Distribute Mission Data & Data Products' {
                                    doc /* Source XMI: _18_5_2_3880181_1510846739503_31105_65235
                                    UML kind: uml:Activity */
                                    in item parameter_0 {
                                        doc /* Source XMI: _18_5_2_3880181_1510846741535_880953_65739
                                        UML parameter name: argument
                                        UML direction: in
                                        UML type: (none) */
                                    }
                                    in item parameter_1 {
                                        doc /* Source XMI: _18_5_2_3880181_1510846741535_420797_65740
                                        UML parameter name: argument
                                        UML direction: in
                                        UML type: (none) */
                                    }
                                    out item parameter_2 {
                                        doc /* Source XMI: _18_5_2_3880181_1510846741535_90381_65741
                                        UML parameter name: result
                                        UML direction: out
                                        UML type: (none) */
                                    }
                                    out item parameter_3 {
                                        doc /* Source XMI: _18_5_2_3880181_1510846741535_146327_65742
                                        UML parameter name: result1
                                        UML direction: out
                                        UML type: (none) */
                                    }
                                    action node_4 {
                                        doc /* Source XMI: _18_5_2_3880181_1510846741535_498599_65743
                                        UML node kind: uml:ActivityParameterNode
                                        UML node name: argument
                                        UML behavior: (none)
                                        UML parameter: _18_5_2_3880181_1510846741535_880953_65739 */
                                    }
                                    action node_5 {
                                        doc /* Source XMI: _18_5_2_3880181_1510846741535_574375_65744
                                        UML node kind: uml:ActivityParameterNode
                                        UML node name: argument
                                        UML behavior: (none)
                                        UML parameter: _18_5_2_3880181_1510846741535_420797_65740 */
                                    }
                                    action node_6 {
                                        doc /* Source XMI: _18_5_2_3880181_1510846741535_524057_65745
                                        UML node kind: uml:ActivityParameterNode
                                        UML node name: result
                                        UML behavior: (none)
                                        UML parameter: _18_5_2_3880181_1510846741535_90381_65741 */
                                    }
                                    action node_7 {
                                        doc /* Source XMI: _18_5_2_3880181_1510846741535_284743_65746
                                        UML node kind: uml:ActivityParameterNode
                                        UML node name: result1
                                        UML behavior: (none)
                                        UML parameter: _18_5_2_3880181_1510846741535_146327_65742 */
                                    }
                                }
                                connection def association_37 {
                                    doc /* Source XMI: _18_5_2_3880181_1510846739503_102435_65236
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Post-Process Mission Data' {
                                        doc /* Source XMI: _18_5_2_3880181_1510846741519_465324_65649
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Distribute Mission Data' {
                                        doc /* Source XMI: _18_5_2_3880181_1510846741535_930841_65747
                                        UML end name: (unnamed) */
                                    }
                                }
                                connection def association_38 {
                                    doc /* Source XMI: _18_5_2_3880181_1510846739503_337823_65237
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Data Products' {
                                        doc /* Source XMI: _18_5_2_3880181_1510846741519_196592_65650
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Distribute Mission Data' {
                                        doc /* Source XMI: _18_5_2_3880181_1510846741535_467003_65748
                                        UML end name: (unnamed) */
                                    }
                                }
                                connection def association_39 {
                                    doc /* Source XMI: _18_5_2_3880181_1510846739503_502516_65238
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Distribute Mission Data & Data Products' {
                                        doc /* Source XMI: _18_5_2_3880181_1510846741519_175908_65651
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Distribute Mission Data' {
                                        doc /* Source XMI: _18_5_2_3880181_1510846741535_160186_65749
                                        UML end name: (unnamed) */
                                    }
                                }
                                action def 'Collect and Distribute Mission Data' {
                                    doc /* Source XMI: _18_5_2_3880181_1510846739503_580396_65239
                                    UML kind: uml:Activity
                                    Source-only uml:ActivityPartition _18_5_2_3880181_1510846741629_110946_65801: {"type": "uml:ActivityPartition", "id": "_18_5_2_3880181_1510846741629_110946_65801", "visibility": "public", "represents": "_18_4_3e4019a_1478803710494_88663_20282"}
                                    Source-only uml:ActivityPartition _18_5_2_3880181_1510846741629_710903_65802: {"type": "uml:ActivityPartition", "id": "_18_5_2_3880181_1510846741629_710903_65802", "visibility": "public", "represents": "_18_0_6_3e4019a_1472151562270_394124_14029"} */
                                    action node_16 {
                                        doc /* Source XMI: _18_5_2_3880181_1510846741629_117943_65794
                                        UML node kind: uml:CallBehaviorAction
                                        UML node name: (unnamed)
                                        UML behavior: _18_5_2_3880181_1510846739488_39328_65203
                                        UML parameter: (none) */
                                        in item pin_1 {
                                            doc /* Source XMI: _18_5_2_3880181_1510846741832_414806_66091
                                            UML pin name: (unnamed)
                                            UML type: (none) */
                                        }
                                        out item pin_2 {
                                            doc /* Source XMI: _18_5_2_3880181_1510846741832_714084_66089
                                            UML pin name: (unnamed)
                                            UML type: (none) */
                                        }
                                        out item pin_3 {
                                            doc /* Source XMI: _18_5_2_3880181_1510846741832_587666_66090
                                            UML pin name: (unnamed)
                                            UML type: (none) */
                                        }
                                    }
                                    action node_17 {
                                        doc /* Source XMI: _18_5_2_3880181_1510846741629_115513_65795
                                        UML node kind: uml:CallBehaviorAction
                                        UML node name: (unnamed)
                                        UML behavior: _18_5_2_3880181_1510846739503_935631_65242
                                        UML parameter: (none) */
                                        in item pin_1 {
                                            doc /* Source XMI: _18_5_2_3880181_1510846741832_967246_66093
                                            UML pin name: (unnamed)
                                            UML type: (none) */
                                        }
                                        out item pin_2 {
                                            doc /* Source XMI: _18_5_2_3880181_1510846741832_880100_66092
                                            UML pin name: (unnamed)
                                            UML type: (none) */
                                        }
                                    }
                                    action node_18 {
                                        doc /* Source XMI: _18_5_2_3880181_1510846741629_960268_65796
                                        UML node kind: uml:InitialNode
                                        UML node name: (unnamed)
                                        UML behavior: (none)
                                        UML parameter: (none) */
                                    }
                                    action node_19 {
                                        doc /* Source XMI: _18_5_2_3880181_1510846741629_805167_65797
                                        UML node kind: uml:ActivityFinalNode
                                        UML node name: (unnamed)
                                        UML behavior: (none)
                                        UML parameter: (none) */
                                    }
                                    action node_20 {
                                        doc /* Source XMI: _18_5_2_3880181_1510846741629_283664_65798
                                        UML node kind: uml:CallBehaviorAction
                                        UML node name: (unnamed)
                                        UML behavior: _18_5_2_3880181_1510846739503_66498_65251
                                        UML parameter: (none) */
                                        out item pin_1 {
                                            doc /* Source XMI: _18_5_2_3880181_1510846741832_868890_66094
                                            UML pin name: (unnamed)
                                            UML type: (none) */
                                        }
                                    }
                                    action node_21 {
                                        doc /* Source XMI: _18_5_2_3880181_1510846741629_980865_65799
                                        UML node kind: uml:CallBehaviorAction
                                        UML node name: (unnamed)
                                        UML behavior: _18_5_2_3880181_1510846739503_691857_65253
                                        UML parameter: (none) */
                                        in item pin_1 {
                                            doc /* Source XMI: _18_5_2_3880181_1510846741832_943817_66095
                                            UML pin name: (unnamed)
                                            UML type: (none) */
                                        }
                                        in item pin_2 {
                                            doc /* Source XMI: _18_5_2_3880181_1510846741832_235153_66096
                                            UML pin name: (unnamed)
                                            UML type: (none) */
                                        }
                                    }
                                    action node_22 {
                                        doc /* Source XMI: _18_5_2_3880181_1510846741629_99173_65800
                                        UML node kind: uml:CallBehaviorAction
                                        UML node name: (unnamed)
                                        UML behavior: _18_5_2_3880181_1510846739503_996945_65252
                                        UML parameter: (none) */
                                        in item pin_1 {
                                            doc /* Source XMI: _18_5_2_3880181_1510846741832_812152_66098
                                            UML pin name: Mission Data Request
                                            UML type: (none) */
                                        }
                                        out item pin_2 {
                                            doc /* Source XMI: _18_5_2_3880181_1510846741832_178191_66097
                                            UML pin name: Mission Tasking
                                            UML type: (none) */
                                        }
                                    }
                                    dependency call_node_16 from node_16 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Distribute Mission Data';
                                    dependency call_node_17 from node_17 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect Mission Data';
                                    dependency call_node_20 from node_20 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Request Mission Data';
                                    dependency call_node_21 from node_21 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Receive Mission Data & Data Products';
                                    dependency call_node_22 from node_22 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Tasking';
                                    flow objectFlow_1 from 'node_17'.pin_2 to 'node_16'.pin_1 {
                                        doc /* Source XMI: _18_5_2_3880181_1510846741629_950827_65803
                                        UML ObjectFlow between indexed node or pin endpoints.
                                        Source-only uml:LiteralUnlimitedNatural _18_5_2_3880181_1510846741832_299422_66099: {"type": "uml:LiteralUnlimitedNatural", "id": "_18_5_2_3880181_1510846741832_299422_66099", "value": "1"} */
                                    }
                                    flow objectFlow_2 from 'node_16'.pin_3 to 'node_21'.pin_1 {
                                        doc /* Source XMI: _18_5_2_3880181_1510846741629_770704_65804
                                        UML ObjectFlow between indexed node or pin endpoints.
                                        Source-only uml:LiteralUnlimitedNatural _18_5_2_3880181_1510846741832_149954_66100: {"type": "uml:LiteralUnlimitedNatural", "id": "_18_5_2_3880181_1510846741832_149954_66100", "value": "1"} */
                                    }
                                    flow objectFlow_3 from 'node_16'.pin_2 to 'node_21'.pin_2 {
                                        doc /* Source XMI: _18_5_2_3880181_1510846741629_483715_65805
                                        UML ObjectFlow between indexed node or pin endpoints.
                                        Source-only uml:LiteralUnlimitedNatural _18_5_2_3880181_1510846741832_641878_66101: {"type": "uml:LiteralUnlimitedNatural", "id": "_18_5_2_3880181_1510846741832_641878_66101", "value": "1"} */
                                    }
                                    succession controlFlow_4 first 'node_18' then 'node_20' {
                                        doc /* Source XMI: _18_5_2_3880181_1510846741629_851209_65806
                                        UML ControlFlow between indexed node endpoints.
                                        Source-only uml:LiteralUnlimitedNatural _18_5_2_3880181_1510846741832_933451_66102: {"type": "uml:LiteralUnlimitedNatural", "id": "_18_5_2_3880181_1510846741832_933451_66102", "value": "1"} */
                                    }
                                    succession controlFlow_5 first 'node_21' then 'node_19' {
                                        doc /* Source XMI: _18_5_2_3880181_1510846741629_393769_65807
                                        UML ControlFlow between indexed node endpoints.
                                        Source-only uml:LiteralUnlimitedNatural _18_5_2_3880181_1510846741832_472886_66103: {"type": "uml:LiteralUnlimitedNatural", "id": "_18_5_2_3880181_1510846741832_472886_66103", "value": "1"} */
                                    }
                                    flow objectFlow_6 from 'node_20'.pin_1 to 'node_22'.pin_1 {
                                        doc /* Source XMI: _18_5_2_3880181_1510846741629_849119_65808
                                        UML ObjectFlow between indexed node or pin endpoints.
                                        Source-only uml:LiteralUnlimitedNatural _18_5_2_3880181_1510846741832_969398_66104: {"type": "uml:LiteralUnlimitedNatural", "id": "_18_5_2_3880181_1510846741832_969398_66104", "value": "1"} */
                                    }
                                    flow objectFlow_7 from 'node_22'.pin_2 to 'node_17'.pin_1 {
                                        doc /* Source XMI: _18_5_2_3880181_1510846741629_727765_65809
                                        UML ObjectFlow between indexed node or pin endpoints.
                                        Source-only uml:LiteralUnlimitedNatural _18_5_2_3880181_1510846741832_222063_66105: {"type": "uml:LiteralUnlimitedNatural", "id": "_18_5_2_3880181_1510846741832_222063_66105", "value": "1"} */
                                    }
                                    part 'property_2' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Distribute Mission Data' {
                                        doc /* Source XMI: _18_5_2_3880181_1510846741519_573129_65669
                                        UML aggregation: composite
                                        UML association: _18_5_2_3880181_1510846739488_735011_65204 */
                                    }
                                    part 'property_3' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect Mission Data' {
                                        doc /* Source XMI: _18_5_2_3880181_1510846741629_338612_65790
                                        UML aggregation: composite
                                        UML association: _18_5_2_3880181_1510846739503_365517_65243 */
                                    }
                                    part 'property_4' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Request Mission Data' {
                                        doc /* Source XMI: _18_5_2_3880181_1510846741629_219642_65791
                                        UML aggregation: composite
                                        UML association: _18_5_2_3880181_1510846739503_95560_65254 */
                                    }
                                    part 'property_5' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Tasking' {
                                        doc /* Source XMI: _18_5_2_3880181_1510846741629_257598_65792
                                        UML aggregation: composite
                                        UML association: _18_5_2_3880181_1510846739503_783640_65255 */
                                    }
                                    part 'property_6' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Receive Mission Data & Data Products' {
                                        doc /* Source XMI: _18_5_2_3880181_1510846741629_438411_65793
                                        UML aggregation: composite
                                        UML association: _18_5_2_3880181_1510846739503_917139_65256 */
                                    }
                                }
                                dependency relationship_41 from OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect and Distribute Mission Data' to OfficialCSRM::'Data'::'02 - CSRM Elements, Examples and Illustrations'::'5 - Architecture'::'L1_Enterprise Example'::'L1.1_Behaviors Example'::'L1.1-1 Collect and Distribute Mission Data  - Example'::'Collect and Distribute Mission Data - Use Case Example'::'CubeSat Mission Enterprise Example'::'Collect Mission Data' {
                                    doc /* Source XMI: _18_5_2_3880181_1510846739503_40763_65240
                                    Stereotype Refine
                                    UML kind: uml:Abstraction */
                                }
                                connection def association_42 {
                                    doc /* Source XMI: _18_5_2_3880181_1510846739503_758648_65241
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Receive Spacecraft Command Sequence' {
                                        doc /* Source XMI: _18_5_2_3880181_1510846741129_446046_65429
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Uplink Spacecraft Command Sequence' {
                                        doc /* Source XMI: _18_5_2_3880181_1510846741629_968056_65812
                                        UML end name: (unnamed) */
                                    }
                                }
                                action def 'Collect Mission Data' {
                                    doc /* Source XMI: _18_5_2_3880181_1510846739503_935631_65242
                                    Comment _18_5_2_3880181_1510846741722_508479_65853
                                    CubeSat Mission Enterprise
                                    UML kind: uml:Activity */
                                    in item parameter_5 {
                                        doc /* Source XMI: _18_5_2_3880181_1510846741629_746683_65813
                                        UML parameter name: Mission Tasking
                                        UML direction: in
                                        UML type: (none) */
                                    }
                                    out item parameter_6 {
                                        doc /* Source XMI: _18_5_2_3880181_1510846741629_141617_65814
                                        UML parameter name: Mission Data
                                        UML direction: out
                                        UML type: (none) */
                                    }
                                    action node_12 {
                                        doc /* Source XMI: _18_5_2_3880181_1510846741722_433259_65858
                                        UML node kind: uml:ActivityParameterNode
                                        UML node name: argument
                                        UML behavior: (none)
                                        UML parameter: _18_5_2_3880181_1510846741629_746683_65813 */
                                    }
                                    action node_13 {
                                        doc /* Source XMI: _18_5_2_3880181_1510846741722_153540_65859
                                        UML node kind: uml:ActivityParameterNode
                                        UML node name: result
                                        UML behavior: (none)
                                        UML parameter: _18_5_2_3880181_1510846741629_141617_65814 */
                                    }
                                    action node_14 {
                                        doc /* Source XMI: _18_5_2_3880181_1510846741722_996117_65860
                                        UML node kind: uml:CallBehaviorAction
                                        UML node name: (unnamed)
                                        UML behavior: _18_5_2_3880181_1510846739488_323227_65199
                                        UML parameter: (none) */
                                        in item pin_0 {
                                            doc /* Source XMI: _18_5_2_3880181_1510846741832_865278_66110
                                            UML pin name: (unnamed)
                                            UML type: (none) */
                                        }
                                        out item pin_1 {
                                            doc /* Source XMI: _18_5_2_3880181_1510846741832_517789_66109
                                            UML pin name: (unnamed)
                                            UML type: (none) */
                                        }
                                    }
                                    action node_15 {
                                        doc /* Source XMI: _18_5_2_3880181_1510846741722_795456_65861
                                        UML node kind: uml:CallBehaviorAction
                                        UML node name: (unnamed)
                                        UML behavior: _18_5_2_3880181_1510846739488_856880_65202
                                        UML parameter: (none) */
                                        in item pin_0 {
                                            doc /* Source XMI: _18_5_2_3880181_1510846741832_971787_66112
                                            UML pin name: Mission Data
                                            UML type: (none) */
                                        }
                                        out item pin_1 {
                                            doc /* Source XMI: _18_5_2_3880181_1510846741832_959226_66111
                                            UML pin name: Mission Data
                                            UML type: (none) */
                                        }
                                    }
                                    action node_16 {
                                        doc /* Source XMI: _18_5_2_3880181_1510846741722_148912_65862
                                        UML node kind: uml:CallBehaviorAction
                                        UML node name: (unnamed)
                                        UML behavior: _18_5_2_3880181_1510846739488_345163_65200
                                        UML parameter: (none) */
                                        in item pin_0 {
                                            doc /* Source XMI: _18_5_2_3880181_1510846741832_897505_66114
                                            UML pin name: (unnamed)
                                            UML type: (none) */
                                        }
                                        out item pin_1 {
                                            doc /* Source XMI: _18_5_2_3880181_1510846741832_509219_66113
                                            UML pin name: (unnamed)
                                            UML type: (none) */
                                        }
                                    }
                                    action node_17 {
                                        doc /* Source XMI: _18_5_2_3880181_1510846741722_473489_65863
                                        UML node kind: uml:CallBehaviorAction
                                        UML node name: (unnamed)
                                        UML behavior: _18_5_2_3880181_1510846739488_740385_65201
                                        UML parameter: (none) */
                                        in item pin_0 {
                                            doc /* Source XMI: _18_5_2_3880181_1510846741832_189517_66116
                                            UML pin name: Spacecraft Command Sequence
                                            UML type: (none) */
                                        }
                                        out item pin_1 {
                                            doc /* Source XMI: _18_5_2_3880181_1510846741832_724947_66115
                                            UML pin name: (unnamed)
                                            UML type: (none) */
                                        }
                                    }
                                    dependency call_node_14 from node_14 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Data Collection & Space-Ground Comm Schedules';
                                    dependency call_node_15 from node_15 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Downlink Mission Data';
                                    dependency call_node_16 from node_16 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Uplink Spacecraft Command Sequence';
                                    dependency call_node_17 from node_17 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect & Pre-Process Mission Data';
                                    flow objectFlow_1 from 'node_12' to 'node_14'.pin_0 {
                                        doc /* Source XMI: _18_5_2_3880181_1510846741722_780687_65864
                                        UML ObjectFlow between indexed node or pin endpoints.
                                        Source-only uml:LiteralUnlimitedNatural _18_5_2_3880181_1510846741832_222896_66117: {"type": "uml:LiteralUnlimitedNatural", "id": "_18_5_2_3880181_1510846741832_222896_66117", "value": "1"} */
                                    }
                                    flow objectFlow_2 from 'node_14'.pin_1 to 'node_16'.pin_0 {
                                        doc /* Source XMI: _18_5_2_3880181_1510846741722_566426_65865
                                        UML ObjectFlow between indexed node or pin endpoints.
                                        Source-only uml:LiteralUnlimitedNatural _18_5_2_3880181_1510846741832_982425_66118: {"type": "uml:LiteralUnlimitedNatural", "id": "_18_5_2_3880181_1510846741832_982425_66118", "value": "1"} */
                                    }
                                    flow objectFlow_3 from 'node_16'.pin_1 to 'node_17'.pin_0 {
                                        doc /* Source XMI: _18_5_2_3880181_1510846741722_52183_65866
                                        UML ObjectFlow between indexed node or pin endpoints.
                                        Source-only uml:LiteralUnlimitedNatural _18_5_2_3880181_1510846741832_896294_66119: {"type": "uml:LiteralUnlimitedNatural", "id": "_18_5_2_3880181_1510846741832_896294_66119", "value": "1"} */
                                    }
                                    flow objectFlow_4 from 'node_17'.pin_1 to 'node_15'.pin_0 {
                                        doc /* Source XMI: _18_5_2_3880181_1510846741722_495262_65867
                                        UML ObjectFlow between indexed node or pin endpoints.
                                        Source-only uml:LiteralUnlimitedNatural _18_5_2_3880181_1510846741832_495453_66120: {"type": "uml:LiteralUnlimitedNatural", "id": "_18_5_2_3880181_1510846741832_495453_66120", "value": "1"} */
                                    }
                                    flow objectFlow_5 from 'node_15'.pin_1 to 'node_13' {
                                        doc /* Source XMI: _18_5_2_3880181_1510846741722_84235_65868
                                        UML ObjectFlow between indexed node or pin endpoints.
                                        Source-only uml:LiteralUnlimitedNatural _18_5_2_3880181_1510846741832_230893_66121: {"type": "uml:LiteralUnlimitedNatural", "id": "_18_5_2_3880181_1510846741832_230893_66121", "value": "1"} */
                                    }
                                    part 'property_1' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Data Collection & Space-Ground Comm Schedules' {
                                        doc /* Source XMI: _18_5_2_3880181_1510846741722_264871_65854
                                        UML aggregation: composite
                                        UML association: _18_5_2_3880181_1510846739503_535865_65245 */
                                    }
                                    part 'property_2' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Uplink Spacecraft Command Sequence' {
                                        doc /* Source XMI: _18_5_2_3880181_1510846741722_483955_65855
                                        UML aggregation: composite
                                        UML association: _18_5_2_3880181_1510846739503_658336_65246 */
                                    }
                                    part 'property_3' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Downlink Mission Data' {
                                        doc /* Source XMI: _18_5_2_3880181_1510846741722_266501_65856
                                        UML aggregation: composite
                                        UML association: _18_5_2_3880181_1510846739503_113225_65247 */
                                    }
                                    part 'property_4' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect & Pre-Process Mission Data' {
                                        doc /* Source XMI: _18_5_2_3880181_1510846741722_220756_65857
                                        UML aggregation: composite
                                        UML association: _18_5_2_3880181_1510846739503_421384_65248 */
                                    }
                                }
                                connection def association_44 {
                                    doc /* Source XMI: _18_5_2_3880181_1510846739503_365517_65243
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect Mission Data' {
                                        doc /* Source XMI: _18_5_2_3880181_1510846741629_338612_65790
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect and Distribute Mission Data' {
                                        doc /* Source XMI: _18_5_2_3880181_1510846741722_492219_65870
                                        UML end name: (unnamed) */
                                    }
                                }
                                connection def association_45 {
                                    doc /* Source XMI: _18_5_2_3880181_1510846739503_244097_65244
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Receive Mission Data' {
                                        doc /* Source XMI: _18_5_2_3880181_1510846741410_263198_65577
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Downlink Mission Data' {
                                        doc /* Source XMI: _18_5_2_3880181_1510846741722_281037_65871
                                        UML end name: (unnamed) */
                                    }
                                }
                                connection def association_46 {
                                    doc /* Source XMI: _18_5_2_3880181_1510846739503_535865_65245
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Data Collection & Space-Ground Comm Schedules' {
                                        doc /* Source XMI: _18_5_2_3880181_1510846741722_264871_65854
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect Mission Data' {
                                        doc /* Source XMI: _18_5_2_3880181_1510846741722_116669_65872
                                        UML end name: (unnamed) */
                                    }
                                }
                                connection def association_47 {
                                    doc /* Source XMI: _18_5_2_3880181_1510846739503_658336_65246
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Uplink Spacecraft Command Sequence' {
                                        doc /* Source XMI: _18_5_2_3880181_1510846741722_483955_65855
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect Mission Data' {
                                        doc /* Source XMI: _18_5_2_3880181_1510846741722_994993_65873
                                        UML end name: (unnamed) */
                                    }
                                }
                                connection def association_48 {
                                    doc /* Source XMI: _18_5_2_3880181_1510846739503_113225_65247
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Downlink Mission Data' {
                                        doc /* Source XMI: _18_5_2_3880181_1510846741722_266501_65856
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect Mission Data' {
                                        doc /* Source XMI: _18_5_2_3880181_1510846741722_691488_65874
                                        UML end name: (unnamed) */
                                    }
                                }
                                connection def association_49 {
                                    doc /* Source XMI: _18_5_2_3880181_1510846739503_421384_65248
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect & Pre-Process Mission Data' {
                                        doc /* Source XMI: _18_5_2_3880181_1510846741722_220756_65857
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect Mission Data' {
                                        doc /* Source XMI: _18_5_2_3880181_1510846741722_47324_65875
                                        UML end name: (unnamed) */
                                    }
                                }
                                dependency relationship_50 from OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect Mission Data' to OfficialCSRM::'Data'::'02 - CSRM Elements, Examples and Illustrations'::'5 - Architecture'::'L1_Enterprise Example'::'L1.1_Behaviors Example'::'L1.1-1 Collect and Distribute Mission Data  - Example'::'Collect and Distribute Mission Data - Use Case Example'::'CubeSat Mission Enterprise Example'::'Collect Mission Data' {
                                    doc /* Source XMI: _18_5_2_3880181_1510846739503_440765_65249
                                    Stereotype Refine
                                    UML kind: uml:Abstraction */
                                }
                                dependency relationship_51 from OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Distribute Mission Data' to OfficialCSRM::'Data'::'02 - CSRM Elements, Examples and Illustrations'::'5 - Architecture'::'L1_Enterprise Example'::'L1.1_Behaviors Example'::'L1.1-1 Collect and Distribute Mission Data  - Example'::'Collect and Distribute Mission Data - Use Case Example'::'CubeSat Mission Enterprise Example'::'Distribute Mission Data' {
                                    doc /* Source XMI: _18_5_2_3880181_1510846739503_659999_65250
                                    Stereotype Refine
                                    UML kind: uml:Abstraction */
                                }
                                action def 'Request Mission Data' {
                                    doc /* Source XMI: _18_5_2_3880181_1510846739503_66498_65251
                                    UML kind: uml:Activity */
                                    out item parameter_0 {
                                        doc /* Source XMI: _18_5_2_3880181_1510846741722_198800_65878
                                        UML parameter name: Mission Data Request
                                        UML direction: out
                                        UML type: (none) */
                                    }
                                    action node_1 {
                                        doc /* Source XMI: _18_5_2_3880181_1510846741722_158091_65879
                                        UML node kind: uml:ActivityParameterNode
                                        UML node name: result
                                        UML behavior: (none)
                                        UML parameter: _18_5_2_3880181_1510846741722_198800_65878 */
                                    }
                                }
                                action def 'Generate Mission Tasking' {
                                    doc /* Source XMI: _18_5_2_3880181_1510846739503_996945_65252
                                    UML kind: uml:Activity
                                    Source-only uml:ActivityPartition _18_5_2_3880181_1510846741801_918568_65926: {"type": "uml:ActivityPartition", "id": "_18_5_2_3880181_1510846741801_918568_65926", "visibility": "public", "represents": "_18_0_6_3e4019a_1472151573820_820968_14607"} */
                                    in item parameter_4 {
                                        doc /* Source XMI: _18_5_2_3880181_1510846741722_379558_65880
                                        UML parameter name: Mission Data Request
                                        UML direction: in
                                        UML type: (none) */
                                    }
                                    out item parameter_5 {
                                        doc /* Source XMI: _18_5_2_3880181_1510846741722_404905_65881
                                        UML parameter name: Mission Tasking
                                        UML direction: out
                                        UML type: (none) */
                                    }
                                    action node_11 {
                                        doc /* Source XMI: _18_5_2_3880181_1510846741801_355411_65921
                                        UML node kind: uml:ActivityParameterNode
                                        UML node name: argument
                                        UML behavior: (none)
                                        UML parameter: _18_5_2_3880181_1510846741722_379558_65880 */
                                    }
                                    action node_12 {
                                        doc /* Source XMI: _18_5_2_3880181_1510846741801_727182_65922
                                        UML node kind: uml:ActivityParameterNode
                                        UML node name: result
                                        UML behavior: (none)
                                        UML parameter: _18_5_2_3880181_1510846741722_404905_65881 */
                                    }
                                    action node_13 {
                                        doc /* Source XMI: _18_5_2_3880181_1510846741801_877635_65923
                                        UML node kind: uml:CallBehaviorAction
                                        UML node name: (unnamed)
                                        UML behavior: _18_5_2_3880181_1510846739519_553785_65265
                                        UML parameter: (none) */
                                        out item pin_1 {
                                            doc /* Source XMI: _18_5_2_3880181_1510846741847_604018_66125
                                            UML pin name: result
                                            UML type: (none) */
                                        }
                                    }
                                    action node_14 {
                                        doc /* Source XMI: _18_5_2_3880181_1510846741801_315315_65924
                                        UML node kind: uml:CallBehaviorAction
                                        UML node name: (unnamed)
                                        UML behavior: _18_5_2_3880181_1510846739519_210337_65266
                                        UML parameter: (none) */
                                        in item pin_1 {
                                            doc /* Source XMI: _18_5_2_3880181_1510846741847_950277_66127
                                            UML pin name: argument
                                            UML type: (none) */
                                        }
                                        out item pin_2 {
                                            doc /* Source XMI: _18_5_2_3880181_1510846741847_312918_66126
                                            UML pin name: result
                                            UML type: (none) */
                                        }
                                    }
                                    action node_15 {
                                        doc /* Source XMI: _18_5_2_3880181_1510846741801_380410_65925
                                        UML node kind: uml:CallBehaviorAction
                                        UML node name: (unnamed)
                                        UML behavior: _18_5_2_3880181_1510846739519_6543_65267
                                        UML parameter: (none) */
                                        in item pin_1 {
                                            doc /* Source XMI: _18_5_2_3880181_1510846741847_957921_66128
                                            UML pin name: argument
                                            UML type: (none) */
                                        }
                                    }
                                    dependency call_node_13 from node_13 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Analyze Mission Data Request';
                                    dependency call_node_14 from node_14 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Develop Mission Tasking';
                                    dependency call_node_15 from node_15 to OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Transmit Mission Tasking';
                                    flow objectFlow_1 from 'node_11' to 'node_13' {
                                        doc /* Source XMI: _18_5_2_3880181_1510846741801_830826_65927
                                        UML ObjectFlow between indexed node or pin endpoints.
                                        Source-only uml:LiteralUnlimitedNatural _18_5_2_3880181_1510846741847_276136_66129: {"type": "uml:LiteralUnlimitedNatural", "id": "_18_5_2_3880181_1510846741847_276136_66129", "value": "1"} */
                                    }
                                    flow objectFlow_2 from 'node_14'.pin_2 to 'node_15'.pin_1 {
                                        doc /* Source XMI: _18_5_2_3880181_1510846741801_631408_65928
                                        UML ObjectFlow between indexed node or pin endpoints.
                                        Source-only uml:LiteralUnlimitedNatural _18_5_2_3880181_1510846741847_816436_66130: {"type": "uml:LiteralUnlimitedNatural", "id": "_18_5_2_3880181_1510846741847_816436_66130", "value": "1"} */
                                    }
                                    flow objectFlow_3 from 'node_15' to 'node_12' {
                                        doc /* Source XMI: _18_5_2_3880181_1510846741801_103210_65929
                                        UML ObjectFlow between indexed node or pin endpoints.
                                        Source-only uml:LiteralUnlimitedNatural _18_5_2_3880181_1510846741847_928405_66131: {"type": "uml:LiteralUnlimitedNatural", "id": "_18_5_2_3880181_1510846741847_928405_66131", "value": "1"} */
                                    }
                                    flow objectFlow_4 from 'node_13'.pin_1 to 'node_14'.pin_1 {
                                        doc /* Source XMI: _18_5_2_3880181_1510846741801_740303_65930
                                        UML ObjectFlow between indexed node or pin endpoints.
                                        Source-only uml:LiteralUnlimitedNatural _18_5_2_3880181_1510846741847_728798_66132: {"type": "uml:LiteralUnlimitedNatural", "id": "_18_5_2_3880181_1510846741847_728798_66132", "value": "1"} */
                                    }
                                    part 'property_1' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Analyze Mission Data Request' {
                                        doc /* Source XMI: _18_5_2_3880181_1510846741801_746218_65918
                                        UML aggregation: composite
                                        UML association: _18_5_2_3880181_1510846739519_256595_65268 */
                                    }
                                    part 'property_2' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Develop Mission Tasking' {
                                        doc /* Source XMI: _18_5_2_3880181_1510846741801_335695_65919
                                        UML aggregation: composite
                                        UML association: _18_5_2_3880181_1510846739519_257595_65269 */
                                    }
                                    part 'property_3' : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Transmit Mission Tasking' {
                                        doc /* Source XMI: _18_5_2_3880181_1510846741801_383493_65920
                                        UML aggregation: composite
                                        UML association: _18_5_2_3880181_1510846739519_16627_65270 */
                                    }
                                }
                                action def 'Receive Mission Data & Data Products' {
                                    doc /* Source XMI: _18_5_2_3880181_1510846739503_691857_65253
                                    UML kind: uml:Activity */
                                    in item parameter_0 {
                                        doc /* Source XMI: _18_5_2_3880181_1510846741801_421069_65932
                                        UML parameter name: Mission Data Products
                                        UML direction: in
                                        UML type: (none) */
                                    }
                                    in item parameter_1 {
                                        doc /* Source XMI: _18_5_2_3880181_1510846741801_930284_65933
                                        UML parameter name: Mission Data
                                        UML direction: in
                                        UML type: (none) */
                                    }
                                    action node_2 {
                                        doc /* Source XMI: _18_5_2_3880181_1510846741801_551385_65934
                                        UML node kind: uml:ActivityParameterNode
                                        UML node name: argument
                                        UML behavior: (none)
                                        UML parameter: _18_5_2_3880181_1510846741801_421069_65932 */
                                    }
                                    action node_3 {
                                        doc /* Source XMI: _18_5_2_3880181_1510846741801_515360_65935
                                        UML node kind: uml:ActivityParameterNode
                                        UML node name: argument
                                        UML behavior: (none)
                                        UML parameter: _18_5_2_3880181_1510846741801_930284_65933 */
                                    }
                                }
                                connection def association_55 {
                                    doc /* Source XMI: _18_5_2_3880181_1510846739503_95560_65254
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Request Mission Data' {
                                        doc /* Source XMI: _18_5_2_3880181_1510846741629_219642_65791
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect and Distribute Mission Data' {
                                        doc /* Source XMI: _18_5_2_3880181_1510846741801_89295_65936
                                        UML end name: (unnamed) */
                                    }
                                }
                                connection def association_56 {
                                    doc /* Source XMI: _18_5_2_3880181_1510846739503_783640_65255
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Tasking' {
                                        doc /* Source XMI: _18_5_2_3880181_1510846741629_257598_65792
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect and Distribute Mission Data' {
                                        doc /* Source XMI: _18_5_2_3880181_1510846741801_275030_65937
                                        UML end name: (unnamed) */
                                    }
                                }
                                connection def association_57 {
                                    doc /* Source XMI: _18_5_2_3880181_1510846739503_917139_65256
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Receive Mission Data & Data Products' {
                                        doc /* Source XMI: _18_5_2_3880181_1510846741629_438411_65793
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Collect and Distribute Mission Data' {
                                        doc /* Source XMI: _18_5_2_3880181_1510846741801_689909_65938
                                        UML end name: (unnamed) */
                                    }
                                }
                                action def 'Maintain Mission Data Collection Schedule' {
                                    doc /* Source XMI: _18_5_2_3880181_1510846739503_398801_65257
                                    UML kind: uml:Activity */
                                    in item parameter_0 {
                                        doc /* Source XMI: _18_5_2_3880181_1510846741801_111283_65939
                                        UML parameter name: (unnamed)
                                        UML direction: in
                                        UML type: (none) */
                                    }
                                    out item parameter_1 {
                                        doc /* Source XMI: _18_5_2_3880181_1510846741801_402295_65940
                                        UML parameter name: Mission Data Collection Schedule
                                        UML direction: out
                                        UML type: (none) */
                                    }
                                    action node_2 {
                                        doc /* Source XMI: _18_5_2_3880181_1510846741801_528373_65941
                                        UML node kind: uml:ActivityParameterNode
                                        UML node name: argument
                                        UML behavior: (none)
                                        UML parameter: _18_5_2_3880181_1510846741801_111283_65939 */
                                    }
                                    action node_3 {
                                        doc /* Source XMI: _18_5_2_3880181_1510846741801_313803_65942
                                        UML node kind: uml:ActivityParameterNode
                                        UML node name: result
                                        UML behavior: (none)
                                        UML parameter: _18_5_2_3880181_1510846741801_402295_65940 */
                                    }
                                }
                                action def 'Maintain Space-Ground Comm Schedule' {
                                    doc /* Source XMI: _18_5_2_3880181_1510846739503_562203_65258
                                    UML kind: uml:Activity */
                                    in item parameter_0 {
                                        doc /* Source XMI: _18_5_2_3880181_1510846741801_449964_65943
                                        UML parameter name: argument
                                        UML direction: in
                                        UML type: (none) */
                                    }
                                    out item parameter_1 {
                                        doc /* Source XMI: _18_5_2_3880181_1510846741801_62724_65944
                                        UML parameter name: Space-Ground Comm Schedule
                                        UML direction: out
                                        UML type: (none) */
                                    }
                                    action node_2 {
                                        doc /* Source XMI: _18_5_2_3880181_1510846741801_746691_65945
                                        UML node kind: uml:ActivityParameterNode
                                        UML node name: argument
                                        UML behavior: (none)
                                        UML parameter: _18_5_2_3880181_1510846741801_449964_65943 */
                                    }
                                    action node_3 {
                                        doc /* Source XMI: _18_5_2_3880181_1510846741801_910704_65946
                                        UML node kind: uml:ActivityParameterNode
                                        UML node name: result
                                        UML behavior: (none)
                                        UML parameter: _18_5_2_3880181_1510846741801_62724_65944 */
                                    }
                                }
                                connection def association_60 {
                                    doc /* Source XMI: _18_5_2_3880181_1510846739503_167238_65259
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Maintain Mission Data Collection Schedule' {
                                        doc /* Source XMI: _18_5_2_3880181_1510846740988_367267_65354
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Data Collection & Space-Ground Comm Schedules' {
                                        doc /* Source XMI: _18_5_2_3880181_1510846741801_592727_65947
                                        UML end name: (unnamed) */
                                    }
                                }
                                connection def association_61 {
                                    doc /* Source XMI: _18_5_2_3880181_1510846739503_11868_65260
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Maintain Space-Ground Comm Schedule' {
                                        doc /* Source XMI: _18_5_2_3880181_1510846740988_61941_65355
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Data Collection & Space-Ground Comm Schedules' {
                                        doc /* Source XMI: _18_5_2_3880181_1510846741801_7789_65948
                                        UML end name: (unnamed) */
                                    }
                                }
                                action def 'Retrieve Space-Ground Comm Command Sequence for Uplink' {
                                    doc /* Source XMI: _18_5_2_3880181_1510846739503_657722_65261
                                    UML kind: uml:Activity */
                                    out item parameter_0 {
                                        doc /* Source XMI: _18_5_2_3880181_1510846741801_790496_65949
                                        UML parameter name: Space-Ground Comm Command Sequence
                                        UML direction: out
                                        UML type: (none) */
                                    }
                                    action node_1 {
                                        doc /* Source XMI: _18_5_2_3880181_1510846741801_65148_65950
                                        UML node kind: uml:ActivityParameterNode
                                        UML node name: result
                                        UML behavior: (none)
                                        UML parameter: _18_5_2_3880181_1510846741801_790496_65949 */
                                    }
                                }
                                connection def association_63 {
                                    doc /* Source XMI: _18_5_2_3880181_1510846739503_292467_65262
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Retrieve Space-Ground Comm Command Sequence for Uplink' {
                                        doc /* Source XMI: _18_5_2_3880181_1510846741129_474186_65430
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Uplink Spacecraft Command Sequence' {
                                        doc /* Source XMI: _18_5_2_3880181_1510846741801_651369_65951
                                        UML end name: (unnamed) */
                                    }
                                }
                                action def 'Retrieve Space-Ground Comm Command Sequence for Downlink' {
                                    doc /* Source XMI: _18_5_2_3880181_1510846739519_775252_65263
                                    UML kind: uml:Activity */
                                    out item parameter_0 {
                                        doc /* Source XMI: _18_5_2_3880181_1510846741801_608720_65952
                                        UML parameter name: result
                                        UML direction: out
                                        UML type: (none) */
                                    }
                                    action node_1 {
                                        doc /* Source XMI: _18_5_2_3880181_1510846741801_609206_65953
                                        UML node kind: uml:ActivityParameterNode
                                        UML node name: result
                                        UML behavior: (none)
                                        UML parameter: _18_5_2_3880181_1510846741801_608720_65952 */
                                    }
                                }
                                connection def association_65 {
                                    doc /* Source XMI: _18_5_2_3880181_1510846739519_228084_65264
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Retrieve Space-Ground Comm Command Sequence for Downlink' {
                                        doc /* Source XMI: _18_5_2_3880181_1510846741410_320792_65578
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Downlink Mission Data' {
                                        doc /* Source XMI: _18_5_2_3880181_1510846741801_572207_65954
                                        UML end name: (unnamed) */
                                    }
                                }
                                action def 'Analyze Mission Data Request' {
                                    doc /* Source XMI: _18_5_2_3880181_1510846739519_553785_65265
                                    UML kind: uml:Activity */
                                    out item parameter_0 {
                                        doc /* Source XMI: _18_5_2_3880181_1510846741801_325251_65955
                                        UML parameter name: result
                                        UML direction: out
                                        UML type: (none) */
                                    }
                                    action node_1 {
                                        doc /* Source XMI: _18_5_2_3880181_1510846741801_216715_65956
                                        UML node kind: uml:ActivityParameterNode
                                        UML node name: result
                                        UML behavior: (none)
                                        UML parameter: _18_5_2_3880181_1510846741801_325251_65955 */
                                    }
                                }
                                action def 'Develop Mission Tasking' {
                                    doc /* Source XMI: _18_5_2_3880181_1510846739519_210337_65266
                                    UML kind: uml:Activity */
                                    out item parameter_0 {
                                        doc /* Source XMI: _18_5_2_3880181_1510846741801_860527_65957
                                        UML parameter name: result
                                        UML direction: out
                                        UML type: (none) */
                                    }
                                    in item parameter_1 {
                                        doc /* Source XMI: _18_5_2_3880181_1510846741801_268951_65958
                                        UML parameter name: argument
                                        UML direction: in
                                        UML type: (none) */
                                    }
                                    action node_2 {
                                        doc /* Source XMI: _18_5_2_3880181_1510846741801_429145_65959
                                        UML node kind: uml:ActivityParameterNode
                                        UML node name: result
                                        UML behavior: (none)
                                        UML parameter: _18_5_2_3880181_1510846741801_860527_65957 */
                                    }
                                    action node_3 {
                                        doc /* Source XMI: _18_5_2_3880181_1510846741801_48295_65960
                                        UML node kind: uml:ActivityParameterNode
                                        UML node name: argument
                                        UML behavior: (none)
                                        UML parameter: _18_5_2_3880181_1510846741801_268951_65958 */
                                    }
                                }
                                action def 'Transmit Mission Tasking' {
                                    doc /* Source XMI: _18_5_2_3880181_1510846739519_6543_65267
                                    UML kind: uml:Activity */
                                    in item parameter_0 {
                                        doc /* Source XMI: _18_5_2_3880181_1510846741801_77352_65961
                                        UML parameter name: argument
                                        UML direction: in
                                        UML type: (none) */
                                    }
                                    action node_1 {
                                        doc /* Source XMI: _18_5_2_3880181_1510846741801_18569_65962
                                        UML node kind: uml:ActivityParameterNode
                                        UML node name: argument
                                        UML behavior: (none)
                                        UML parameter: _18_5_2_3880181_1510846741801_77352_65961 */
                                    }
                                }
                                connection def association_69 {
                                    doc /* Source XMI: _18_5_2_3880181_1510846739519_256595_65268
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Analyze Mission Data Request' {
                                        doc /* Source XMI: _18_5_2_3880181_1510846741801_746218_65918
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Tasking' {
                                        doc /* Source XMI: _18_5_2_3880181_1510846741801_273664_65963
                                        UML end name: (unnamed) */
                                    }
                                }
                                connection def association_70 {
                                    doc /* Source XMI: _18_5_2_3880181_1510846739519_257595_65269
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Develop Mission Tasking' {
                                        doc /* Source XMI: _18_5_2_3880181_1510846741801_335695_65919
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Tasking' {
                                        doc /* Source XMI: _18_5_2_3880181_1510846741801_232132_65964
                                        UML end name: (unnamed) */
                                    }
                                }
                                connection def association_71 {
                                    doc /* Source XMI: _18_5_2_3880181_1510846739519_16627_65270
                                    UML end details are in the source map (SysML v2 connector ends have fixed [1..1] multiplicity). */
                                    end end1 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Transmit Mission Tasking' {
                                        doc /* Source XMI: _18_5_2_3880181_1510846741801_383493_65920
                                        UML end name: (unnamed) */
                                    }
                                    end end2 : OfficialCSRM::'Data'::'02 - CSRM Elements, Examples and Illustrations'::'5 - Architecture'::'L1_Enterprise Example'::'L1.1_Behaviors Example'::'L1.1-1 Collect and Distribute Mission Data  - Example'::'Collect and Distribute Mission Data - Activity Example'::'Generate Mission Tasking' {
                                        doc /* Source XMI: _18_5_2_3880181_1510846741801_150780_65965
                                        UML end name: (unnamed) */
                                    }
                                }
                            }
                            package 'Actors' {
                                doc /* Source XMI: _18_0_6_3e4019a_1473981576645_53606_17189
                                UML kind: uml:Package */
                                part def 'Chief Scientist' {
                                    @OfficialCSRMProfile::'Architecture Structures Profile'::'Stakeholder';
                                    doc /* Source XMI: _18_4_3e4019a_1478803710494_88663_20282
                                    Stereotype Stakeholder
                                    UML kind: uml:Class */
                                    action def 'Request Mission Data' {
                                        doc /* Source XMI: _18_4_3e4019a_1478803803952_468431_20400
                                        UML operation. Method reference: _18_5_2_3880181_1510846739503_66498_65251 */
                                        out item parameter_1 {
                                            doc /* Source XMI: _18_4_3e4019a_1478803842667_235926_20420
                                            UML parameter name: Mission Data Request
                                            UML direction: out
                                            UML type: (none) */
                                        }
                                    }
                                    action def 'Receive Mission Data & Data Products' {
                                        doc /* Source XMI: _18_4_3e4019a_1478803816635_710889_20405
                                        UML operation. Method reference: _18_5_2_3880181_1510846739503_691857_65253 */
                                        in item parameter_1 {
                                            doc /* Source XMI: _18_4_3e4019a_1478803868811_739393_20427
                                            UML parameter name: Mission Data Products
                                            UML direction: in
                                            UML type: (none) */
                                        }
                                        in item parameter_2 {
                                            doc /* Source XMI: _18_4_3e4019a_1478803868815_513231_20428
                                            UML parameter name: Mission Data
                                            UML direction: in
                                            UML type: (none) */
                                        }
                                    }
                                }
                            }
                        }
                    }
                }
            }
            package '6 - Data Models' {
                doc /* Source XMI: _19_0_2_3880181_1612801776414_252243_62543
                UML kind: uml:Package */
                package 'L1_Enterprise Data Model - Example' {
                    doc /* Source XMI: _19_0_2_3880181_1638369336699_97429_56409
                    UML kind: uml:Package */
                    part def 'Mission Data Collection Command Sequence' {
                        doc /* Source XMI: _19_0_2_3880181_1638368987199_859393_56263
                        Stereotype Block
                        UML kind: uml:Class */
                    }
                    part def 'Mission Data Collection Schedule' {
                        doc /* Source XMI: _19_0_2_3880181_1638368940825_34437_56261
                        Stereotype Block
                        UML kind: uml:Class */
                    }
                    part def 'Mission Data Products' {
                        doc /* Source XMI: _19_0_2_3880181_1638369079845_444989_56265
                        Stereotype Block
                        UML kind: uml:Class */
                    }
                    part def 'Mission Data Request' {
                        doc /* Source XMI: _19_0_2_3880181_1638368647072_359431_56251
                        Stereotype Block
                        UML kind: uml:Class */
                    }
                    part def 'Mission Data' {
                        doc /* Source XMI: _19_0_2_3880181_1638369175948_828387_56271
                        Stereotype Block
                        UML kind: uml:Class */
                    }
                    part def 'Mission Tasking' {
                        doc /* Source XMI: _19_0_2_3880181_1638369111669_363658_56267
                        Stereotype Block
                        UML kind: uml:Class */
                    }
                    part def 'Post-Processed Mission Data' {
                        doc /* Source XMI: _19_0_2_3880181_1638368829778_484632_56257
                        Stereotype Block
                        UML kind: uml:Class */
                    }
                    part def 'Required Mission Data' {
                        doc /* Source XMI: _19_0_2_3880181_1638368889528_308130_56259
                        Stereotype Block
                        UML kind: uml:Class */
                    }
                    part def 'Space-Gound Comm Command Seqeunce' {
                        doc /* Source XMI: _19_0_2_3880181_1638368714151_55903_56255
                        Stereotype Block
                        Comment _19_0_2_3880181_1638376410610_252004_56298
                        Maintained on-board
                        UML kind: uml:Class */
                    }
                    part def 'Space-Ground Comm Schedule' {
                        doc /* Source XMI: _19_0_2_3880181_1638368681307_776033_56253
                        Stereotype Block
                        Comment _19_0_2_3880181_1638376460641_984029_56299
                        Maintained on-board
                        UML kind: uml:Class */
                    }
                    part def 'Spacecraft Command Sequence' {
                        doc /* Source XMI: _19_0_2_3880181_1638369136886_629020_56269
                        Stereotype Block
                        Comment _19_0_2_3880181_1638376810939_838979_56300
                        Contains Mission Data Collection Schedule and Space-Ground Comm Schedule
                        UML kind: uml:Class */
                    }
                }
            }
            package '4 - Requirememts' {
                doc /* Source XMI: _19_0_2_3880181_1612801823540_466026_62544
                UML kind: uml:Package */
                package 'L1_Enterprise Requrements Example' {
                    doc /* Source XMI: _19_0_2_3880181_1639684291188_978409_57166
                    UML kind: uml:Package */
                    part def 'Mission Rqts Group' {
                        @OfficialCSRMProfile::'Concerns and Requirements Profile'::'Group';
                        doc /* Source XMI: _19_0_2_3880181_1639684933986_717823_57325
                        Stereotype Group: Text=The Group provides the prefix and numbering scheme which is easy to change., Id=1
                        UML kind: uml:Class */
                    }
                    requirement def 'Requirement A Name' {
                        @OfficialCSRMProfile::'Concerns and Requirements Profile'::'MissionRequirement';
                        doc /* Requirement A shall statement */
                        comment /* Source XMI: _19_0_2_3880181_1639684933986_644907_57326
                        Stereotype MissionRequirement: Text=Requirement A shall statement, Id=2
                        UML kind: uml:Class */
                    }
                    requirement def 'Requirement B Name' {
                        @OfficialCSRMProfile::'Concerns and Requirements Profile'::'MissionRequirement';
                        doc /* Requirement B shall statement */
                        comment /* Source XMI: _19_0_2_3880181_1639788313688_589868_57507
                        Stereotype MissionRequirement: Text=Requirement B shall statement, Id=3
                        UML kind: uml:Class */
                    }
                }
            }
            package '7 - Validation Verification' {
                doc /* Source XMI: _19_0_2_3880181_1612801863992_484569_62545
                UML kind: uml:Package */
                package 'Validation Verification - Concepts - Illustration' {
                    doc /* Source XMI: _18_5_2_3880181_1554842289376_283169_65189
                    Comment _19_0_2_3880181_1601128021431_100478_62711
                    An example population of relationships that can be established between Validation Activities, Verification Activities, Stakeholders, Technical Measures, and Rqts.
                    Comment _19_0_3_2b0010b_1619541491687_14173_29029 (Explanation)
                    This package diagram is a proof-of-concept for one way of incorporating Validation and Verification in the CSRM.
                    ValidationActivity and VerificationActivity stereotypes have been defined.
                    Note that these stereotypes are ''ordinary" SysML elements.
                    They are not SysML Activity elements, which might a bit advanced for a university mission team.
                    However a future release of the CSRM could include validation and verification using SysML Activity elements
                    Comment _19_0_3_2b0010b_1619547271175_882183_32838 (Explanation)
                    Validation confirms, by providing objective evidence, that the system, as-built (or as it will be built), satisfies the stakeholders’ needs, objectives, and moes. That is, the right system has been (or will be) built.
                    Comment _19_0_3_2b0010b_1619547271190_252864_32871 (Explanation)
                    Verification confirms, by providing objective evidence, that the system and all its elements perform their intended functions and satisfy the requirements allocated to them. That is, the system has been built right.
                    Comment _19_0_3_2b0010b_1619547271186_89278_32860 (Explanation)
                    This is an illustration of the types of relationships that can be established between Validation Activities, Verification Activities, Stakeholders, Technical Measures, and Requirements.
                    Comment _19_0_2_3880181_1638988388388_645050_57503 (Explanation)
                    Validation and Verification - Concepts - Illustration
                    UML kind: uml:Package */
                    requirement def 'MissionRequirement-1' {
                        @OfficialCSRMProfile::'Concerns and Requirements Profile'::'MissionRequirement';
                        comment /* Source XMI: _18_5_2_3880181_1554843069169_853894_65310
                        Stereotype MissionRequirement: Text=, Id=1
                        UML kind: uml:Class */
                    }
                    part def 'MoeSpecification-1' {
                        @OfficialCSRMProfile::'Technical Measures Profile'::'moeSpecification';
                        doc /* Source XMI: _18_5_2_3880181_1554854968790_404162_65849
                        Stereotype moeSpecification: Id=
                        UML kind: uml:Class */
                    }
                    part def 'MissionObjective-1' {
                        @OfficialCSRMProfile::'Concerns and Requirements Profile'::'MissionObjective';
                        doc /* Source XMI: _18_5_2_3880181_1554912866728_682360_66684
                        Stereotype MissionObjective: Text=, Id=2
                        UML kind: uml:Class */
                    }
                    part def 'Stakeholder-A' {
                        doc /* Source XMI: _18_5_2_3880181_1554923192261_761841_65917
                        Stereotype Stakeholder
                        UML kind: uml:Actor */
                    }
                    part def 'Stakeholder-B' {
                        doc /* Source XMI: _18_5_2_3880181_1554923258276_635239_65919
                        Stereotype Stakeholder
                        UML kind: uml:Actor */
                    }
                    part def 'Enterprise-X' {
                        doc /* Source XMI: _18_5_2_3880181_1554987455624_656486_65389
                        Stereotype Block
                        UML kind: uml:Class */
                        attribute 'myMOE' {
                            doc /* Source XMI: _19_0_3_2b0010b_1619544968085_38127_30093
                            Stereotype ValueProperty
                            Stereotype moe
                            UML aggregation: composite
                            UML association: none
                            External type: http://www.omg.org/spec/SysML/20181001/SysML.xmi#SysML_dataType.Real */
                        }
                    }
                    part def 'Subsystem-X' {
                        doc /* Source XMI: _18_5_2_3880181_1554988665991_968538_67828
                        Stereotype Subsystem
                        UML kind: uml:Class */
                    }
                    dependency relationship_13 from OfficialCSRM::'Data'::'02 - CSRM Elements, Examples and Illustrations'::'7 - Validation Verification'::'Validation Verification - Concepts - Illustration'::'Subsystem-X' to OfficialCSRM::'Data'::'02 - CSRM Elements, Examples and Illustrations'::'7 - Validation Verification'::'Validation Verification - Concepts - Illustration'::'MissionRequirement-1' {
                        doc /* Source XMI: _18_5_2_3880181_1554988799469_851524_67867
                        Stereotype Satisfy
                        UML kind: uml:Abstraction */
                    }
                    action def 'VerificationActivity-1' {
                        @OfficialCSRMProfile::'Validation and Verification Profile'::'VerificationActivity';
                        doc /* Source XMI: _19_0_3_2b0010b_1613330522338_942567_9130
                        Stereotype TestCase
                        Stereotype VerificationActivity
                        UML kind: uml:Activity */
                        out item parameter_0 {
                            doc /* Source XMI: _19_0_3_2b0010b_1613330522349_213055_9156
                            UML parameter name: verdict
                            UML direction: return
                            UML type: http://www.omg.org/spec/SysML/20181001/SysML.xmi#SysML_dataType.VerdictKind */
                        }
                        action node_1 {
                            doc /* Source XMI: _19_0_3_2b0010b_1613330522357_933146_9159
                            UML node kind: uml:ActivityParameterNode
                            UML node name: verdict
                            UML behavior: (none)
                            UML parameter: _19_0_3_2b0010b_1613330522349_213055_9156 */
                        }
                    }
                    action def 'ValidationActivity-1' {
                        @OfficialCSRMProfile::'Validation and Verification Profile'::'ValidationActivity';
                        doc /* Source XMI: _19_0_3_2b0010b_1613330558252_640243_9171
                        Stereotype ValidationActivity
                        UML kind: uml:Activity */
                        out item parameter_0 {
                            doc /* Source XMI: _19_0_3_2b0010b_1613330558261_972596_9197
                            UML parameter name: verdict
                            UML direction: return
                            UML type: http://www.omg.org/spec/SysML/20181001/SysML.xmi#SysML_dataType.VerdictKind */
                        }
                        action node_1 {
                            doc /* Source XMI: _19_0_3_2b0010b_1613330558270_299548_9198
                            UML node kind: uml:ActivityParameterNode
                            UML node name: verdict
                            UML behavior: (none)
                            UML parameter: _19_0_3_2b0010b_1613330558261_972596_9197 */
                        }
                    }
                    action def 'ValidationActivity-2' {
                        @OfficialCSRMProfile::'Validation and Verification Profile'::'ValidationActivity';
                        doc /* Source XMI: _19_0_3_2b0010b_1613330560935_399735_9206
                        Stereotype ValidationActivity
                        UML kind: uml:Activity */
                        out item parameter_0 {
                            doc /* Source XMI: _19_0_3_2b0010b_1613330560949_356886_9232
                            UML parameter name: verdict
                            UML direction: return
                            UML type: http://www.omg.org/spec/SysML/20181001/SysML.xmi#SysML_dataType.VerdictKind */
                        }
                        action node_1 {
                            doc /* Source XMI: _19_0_3_2b0010b_1613330560952_53665_9233
                            UML node kind: uml:ActivityParameterNode
                            UML node name: verdict
                            UML behavior: (none)
                            UML parameter: _19_0_3_2b0010b_1613330560949_356886_9232 */
                        }
                    }
                    dependency relationship_17 from OfficialCSRM::'Data'::'02 - CSRM Elements, Examples and Illustrations'::'7 - Validation Verification'::'Validation Verification - Concepts - Illustration'::'ValidationActivity-1' to OfficialCSRM::'Data'::'02 - CSRM Elements, Examples and Illustrations'::'7 - Validation Verification'::'Validation Verification - Concepts - Illustration'::'MissionObjective-1' {
                        @OfficialCSRMProfile::'Validation and Verification Profile'::'Validation';
                        doc /* Source XMI: _19_0_2_3880181_1556049902496_987992_61639
                        Stereotype Validation
                        UML kind: uml:Abstraction */
                    }
                    dependency relationship_18 from OfficialCSRM::'Data'::'02 - CSRM Elements, Examples and Illustrations'::'7 - Validation Verification'::'Validation Verification - Concepts - Illustration'::'ValidationActivity-2' to OfficialCSRM::'Data'::'02 - CSRM Elements, Examples and Illustrations'::'7 - Validation Verification'::'Validation Verification - Concepts - Illustration'::'MoeSpecification-1' {
                        @OfficialCSRMProfile::'Validation and Verification Profile'::'Validation';
                        doc /* Source XMI: _19_0_2_3880181_1556049953104_37342_61643
                        Stereotype Validation
                        UML kind: uml:Abstraction */
                    }
                    dependency relationship_19 from OfficialCSRM::'Data'::'02 - CSRM Elements, Examples and Illustrations'::'7 - Validation Verification'::'Validation Verification - Concepts - Illustration'::'VerificationActivity-1' to OfficialCSRM::'Data'::'02 - CSRM Elements, Examples and Illustrations'::'7 - Validation Verification'::'Validation Verification - Concepts - Illustration'::'MissionRequirement-1' {
                        @OfficialCSRMProfile::'Validation and Verification Profile'::'Verification';
                        doc /* Source XMI: _19_0_3_2b0010b_1613337985129_656125_14446
                        Stereotype Verification
                        UML kind: uml:Abstraction */
                    }
                    dependency relationship_20 from OfficialCSRM::'Data'::'02 - CSRM Elements, Examples and Illustrations'::'7 - Validation Verification'::'Validation Verification - Concepts - Illustration'::'MissionRequirement-1' to OfficialCSRM::'Data'::'02 - CSRM Elements, Examples and Illustrations'::'7 - Validation Verification'::'Validation Verification - Concepts - Illustration'::'MissionObjective-1' {
                        doc /* Source XMI: _19_0_3_2b0010b_1619541389912_524426_28957
                        Stereotype DeriveReqt
                        UML kind: uml:Abstraction */
                    }
                    dependency relationship_21 from OfficialCSRM::'Data'::'02 - CSRM Elements, Examples and Illustrations'::'7 - Validation Verification'::'Validation Verification - Concepts - Illustration'::'MissionObjective-1' to OfficialCSRM::'Data'::'02 - CSRM Elements, Examples and Illustrations'::'7 - Validation Verification'::'Validation Verification - Concepts - Illustration'::'MoeSpecification-1' {
                        doc /* Source XMI: _19_0_3_2b0010b_1619541406079_582793_28972
                        Stereotype Refine
                        UML kind: uml:Abstraction */
                    }
                    requirement def 'MoeRequirement-1' {
                        @OfficialCSRMProfile::'Technical Measures Profile'::'moeRequirement';
                        comment /* Source XMI: _19_0_3_2b0010b_1619544921953_730895_30046
                        Stereotype moeRequirement: Text=, Id=3
                        UML kind: uml:Class */
                    }
                    dependency relationship_23 from OfficialCSRM::'Data'::'02 - CSRM Elements, Examples and Illustrations'::'7 - Validation Verification'::'Validation Verification - Concepts - Illustration'::'Enterprise-X'::'myMOE' to OfficialCSRM::'Data'::'02 - CSRM Elements, Examples and Illustrations'::'7 - Validation Verification'::'Validation Verification - Concepts - Illustration'::'MoeRequirement-1' {
                        doc /* Source XMI: _19_0_3_2b0010b_1619544998775_576703_30099
                        Stereotype Satisfy
                        UML kind: uml:Abstraction */
                    }
                    dependency relationship_24 from OfficialCSRM::'Data'::'02 - CSRM Elements, Examples and Illustrations'::'7 - Validation Verification'::'Validation Verification - Concepts - Illustration'::'ValidationActivity-2' to OfficialCSRM::'Data'::'02 - CSRM Elements, Examples and Illustrations'::'7 - Validation Verification'::'Validation Verification - Concepts - Illustration'::'MoeRequirement-1' {
                        doc /* Source XMI: _19_0_3_2b0010b_1619545264655_838564_30111
                        UML kind: uml:Abstraction */
                    }
                    dependency relationship_25 from OfficialCSRM::'Data'::'02 - CSRM Elements, Examples and Illustrations'::'7 - Validation Verification'::'Validation Verification - Concepts - Illustration'::'MoeSpecification-1' to OfficialCSRM::'Data'::'02 - CSRM Elements, Examples and Illustrations'::'7 - Validation Verification'::'Validation Verification - Concepts - Illustration'::'Stakeholder-B' {
                        @OfficialCSRMProfile::'Architecture Structures Profile'::'ConcernOf';
                        doc /* Source XMI: _19_0_3_2b0010b_1619652010381_762245_34585
                        Stereotype ConcernOf
                        UML kind: uml:Dependency */
                    }
                    dependency relationship_26 from OfficialCSRM::'Data'::'02 - CSRM Elements, Examples and Illustrations'::'7 - Validation Verification'::'Validation Verification - Concepts - Illustration'::'MissionObjective-1' to OfficialCSRM::'Data'::'02 - CSRM Elements, Examples and Illustrations'::'7 - Validation Verification'::'Validation Verification - Concepts - Illustration'::'Stakeholder-A' {
                        @OfficialCSRMProfile::'Architecture Structures Profile'::'ConcernOf';
                        doc /* Source XMI: _19_0_3_2b0010b_1619652054114_231472_34592
                        Stereotype ConcernOf
                        UML kind: uml:Dependency */
                    }
                    dependency relationship_27 from OfficialCSRM::'Data'::'02 - CSRM Elements, Examples and Illustrations'::'7 - Validation Verification'::'Validation Verification - Concepts - Illustration'::'MoeSpecification-1' to OfficialCSRM::'Data'::'02 - CSRM Elements, Examples and Illustrations'::'7 - Validation Verification'::'Validation Verification - Concepts - Illustration'::'MoeRequirement-1' {
                        doc /* Source XMI: _19_0_3_2b0010b_1619798880666_133369_52941
                        Stereotype Refine
                        UML kind: uml:Abstraction */
                    }
                    dependency relationship_28 from OfficialCSRM::'Data'::'02 - CSRM Elements, Examples and Illustrations'::'7 - Validation Verification'::'Validation Verification - Concepts - Illustration'::'MoeSpecification-1' to OfficialCSRM::'Data'::'02 - CSRM Elements, Examples and Illustrations'::'7 - Validation Verification'::'Validation Verification - Concepts - Illustration'::'MoeRequirement-1' {
                        doc /* Source XMI: _19_0_2_3880181_1638901256828_789315_56341
                        Stereotype Refine
                        UML kind: uml:Abstraction */
                    }
                    dependency relationship_29 from OfficialCSRM::'Data'::'02 - CSRM Elements, Examples and Illustrations'::'7 - Validation Verification'::'Validation Verification - Concepts - Illustration'::'Enterprise-X' to OfficialCSRM::'Data'::'02 - CSRM Elements, Examples and Illustrations'::'7 - Validation Verification'::'Validation Verification - Concepts - Illustration'::'MoeRequirement-1' {
                        doc /* Source XMI: _19_0_2_3880181_1638901722238_652265_56370
                        UML kind: uml:Dependency */
                    }
                    dependency relationship_30 from OfficialCSRM::'Data'::'02 - CSRM Elements, Examples and Illustrations'::'7 - Validation Verification'::'Validation Verification - Concepts - Illustration'::'ValidationActivity-2' to OfficialCSRM::'Data'::'02 - CSRM Elements, Examples and Illustrations'::'7 - Validation Verification'::'Validation Verification - Concepts - Illustration'::'MoeSpecification-1' {
                        doc /* Source XMI: _19_0_2_3880181_1638901807660_792083_56373
                        UML kind: uml:Dependency */
                    }
                    dependency relationship_31 from OfficialCSRM::'Data'::'02 - CSRM Elements, Examples and Illustrations'::'7 - Validation Verification'::'Validation Verification - Concepts - Illustration'::'MissionRequirement-1' to OfficialCSRM::'Data'::'02 - CSRM Elements, Examples and Illustrations'::'7 - Validation Verification'::'Validation Verification - Concepts - Illustration'::'MissionObjective-1' {
                        doc /* Source XMI: _19_0_2_3880181_1638903068726_949661_56515
                        Stereotype DeriveReqt
                        UML kind: uml:Abstraction */
                    }
                    dependency relationship_32 from OfficialCSRM::'Data'::'02 - CSRM Elements, Examples and Illustrations'::'7 - Validation Verification'::'Validation Verification - Concepts - Illustration'::'MoeSpecification-1' to OfficialCSRM::'Data'::'02 - CSRM Elements, Examples and Illustrations'::'7 - Validation Verification'::'Validation Verification - Concepts - Illustration'::'Stakeholder-B' {
                        @OfficialCSRMProfile::'Architecture Structures Profile'::'ConcernOf';
                        doc /* Source XMI: _19_0_2_3880181_1638903554866_258874_56555
                        Stereotype ConcernOf
                        UML kind: uml:Dependency */
                    }
                    action def 'VerificationActivity-2' {
                        @OfficialCSRMProfile::'Validation and Verification Profile'::'VerificationActivity';
                        doc /* Source XMI: _19_0_2_3880181_1638903757880_178281_56561
                        Stereotype TestCase
                        Stereotype VerificationActivity
                        UML kind: uml:Activity */
                        out item parameter_0 {
                            doc /* Source XMI: _19_0_2_3880181_1638903757880_145865_56562
                            UML parameter name: verdict
                            UML direction: return
                            UML type: http://www.omg.org/spec/SysML/20181001/SysML.xmi#SysML_dataType.VerdictKind */
                        }
                        action node_1 {
                            doc /* Source XMI: _19_0_2_3880181_1638903757880_910462_56563
                            UML node kind: uml:ActivityParameterNode
                            UML node name: verdict
                            UML behavior: (none)
                            UML parameter: _19_0_2_3880181_1638903757880_145865_56562 */
                        }
                    }
                    dependency relationship_34 from OfficialCSRM::'Data'::'02 - CSRM Elements, Examples and Illustrations'::'7 - Validation Verification'::'Validation Verification - Concepts - Illustration'::'VerificationActivity-2' to OfficialCSRM::'Data'::'02 - CSRM Elements, Examples and Illustrations'::'7 - Validation Verification'::'Validation Verification - Concepts - Illustration'::'MoeRequirement-1' {
                        doc /* Source XMI: _19_0_2_3880181_1638903809068_437517_56590
                        UML kind: uml:Dependency */
                    }
                    dependency relationship_35 from OfficialCSRM::'Data'::'02 - CSRM Elements, Examples and Illustrations'::'7 - Validation Verification'::'Validation Verification - Concepts - Illustration'::'VerificationActivity-2' to OfficialCSRM::'Data'::'02 - CSRM Elements, Examples and Illustrations'::'7 - Validation Verification'::'Validation Verification - Concepts - Illustration'::'MoeRequirement-1' {
                        doc /* Source XMI: _19_0_2_3880181_1638910079430_512295_56481
                        Stereotype Verify
                        UML kind: uml:Abstraction */
                    }
                    dependency relationship_36 from OfficialCSRM::'Data'::'02 - CSRM Elements, Examples and Illustrations'::'7 - Validation Verification'::'Validation Verification - Concepts - Illustration'::'MissionObjective-1' to OfficialCSRM::'Data'::'02 - CSRM Elements, Examples and Illustrations'::'7 - Validation Verification'::'Validation Verification - Concepts - Illustration'::'Stakeholder-A' {
                        doc /* Source XMI: _19_0_2_3880181_1638912182298_227131_56832
                        Stereotype Trace
                        UML kind: uml:Abstraction */
                    }
                    dependency relationship_37 from OfficialCSRM::'Data'::'02 - CSRM Elements, Examples and Illustrations'::'7 - Validation Verification'::'Validation Verification - Concepts - Illustration'::'MoeSpecification-1' to OfficialCSRM::'Data'::'02 - CSRM Elements, Examples and Illustrations'::'7 - Validation Verification'::'Validation Verification - Concepts - Illustration'::'Stakeholder-B' {
                        doc /* Source XMI: _19_0_2_3880181_1638912356656_747110_56843
                        Stereotype Trace
                        UML kind: uml:Abstraction */
                    }
                }
            }
            package '8 - CSRM Population' {
                doc /* Source XMI: _18_5_2_3880181_1552247476525_922944_67947
                Comment _19_0_2_3880181_1600787738958_955086_62993
                Package containing an illustration of the CSRM elements along with CSRM element population package diagrams.
                Comment _19_0_2_3880181_1657567678920_50130_58802 (Explanation)
                CSRM Elements, Examples and Illusrations
                UML kind: uml:Package */
                package '8.2 - CSRM Elements' {
                    doc /* Source XMI: _18_5_2_3880181_1550588335855_478944_65126
                    Comment _19_0_3_2b0010b_1619532094165_518699_13979 (Explanation, HowTo)
                    Select Architectural Element
                    Select Edit Compartments
                    Select Element Properties
                    Select Part
                    Move from Hidden to Selected
                    Select Architectural Element
                    Select Part property
                    Select Directed Composition
                    Drag to Part element
                    Comment _19_0_3_2b0010b_1619532094169_418561_13990 (HowTo)
                    Set font size
                    Select Element
                    Select Symbol Properties
                    Select Font
                    Select Ellipses
                    Select 14
                    Select Show Stereotypes
                    Select Text, or .....
                    Comment _19_0_3_2b0010b_1619532094178_559416_14012 (Explanation)
                    A Technical Measure Specification captures the descriptions of technical measures in textual form.  Stakeholders will likely describe their technical measures as text.
                    They will communicate and negotiate these descriptions with engineers who will transform them into measures that can be tracked and assessed
                    The Technical Measure is specified as a value property of an enterprise, segment or subsystem element..
                    Comment _19_0_3_2b0010b_1619532094183_177554_14023 (Explanation)
                    The CSRM is a logical model consisting of model elements and diagrams.  Shown below are CSRM elements and example element properties.
                    The Mission-specific CubeSat Model (MCM) is based on the CSRM.  The MCM provide the basis for design and development of the mission-specific CubeSat.
                    The mission team identifies the systems engineering methodology to be followed and then updates the MCM organization, elements, element properties, relationships, and diagrams as follows:
                    1) Determine if the CSRM elements are necessary and sufficient.  If not, modify accordingly.
                    2) Identify stakeholders and stakeholder terminology such as concerns, needs, objectives, and constraints, as they relate to establishing mission requirements.
                    3) Establish the relationships between use cases, technical measures, and space and ground segment and subsystems requirements.  These relationships can be exhibited in model artifacts such as requirement tables, requirement diagrams, and dependency matrices.
                    4) Identify the model artifacts that are needed such as for: stakeholder buy-off, internal and external design reviews, and design specifications.
                    Comment _19_0_3_2b0010b_1619532094191_12910_14034 (Explanation)
                    A Behavior can be specified by a Behavior description, a Use Case diagram, or an Activity diagram
                    Comment _19_0_3_2b0010b_1619532094194_234431_14045 (Explanation)
                    The validation process can be captured in a:
                    1) Validation Activity
                    element properties, or
                    2) Validation Activity Diagram, or
                    3) Validation Activity Word document
                    Comment _19_0_3_2b0010b_1619532094198_567447_14056 (HowTo)
                    Select CSRM Elements
                    Select Create Element
                    Select Element
                    Comment _19_0_3_2b0010b_1619532094202_198795_14067 (HowTo)
                    Select Properties
                    Select Element
                    Select Edit Compartments
                    Select Element Properties
                    Select form Hidden and move to Selected
                    Comment _19_0_3_2b0010b_1619532094205_702138_14078 (HowTo)
                    Populate element properties
                    Select element
                    Select specification
                    Select a property
                    Select "emptyt box" to reveal eipses
                    Select ellipses
                    and depending on the property enter text or use the search function to locate and populate relational element
                    UML kind: uml:Package */
                    part def 'Subsystem' {
                        doc /* Source XMI: _18_5_2_3880181_1550588639328_17040_65442
                        Stereotype Subsystem
                        UML kind: uml:Class */
                        part 'component' : OfficialCSRM::'Data'::'02 - CSRM Elements, Examples and Illustrations'::'8 - CSRM Population'::'8.2 - CSRM Elements'::'Component' {
                            doc /* Source XMI: _18_5_2_3880181_1550854076077_816754_66139
                            Stereotype PartProperty
                            UML aggregation: composite
                            UML association: _18_5_2_3880181_1550854076077_525949_66138 */
                        }
                    }
                    part def 'Component' {
                        @OfficialCSRMProfile::'Architecture Structures Profile'::'Component';
                        doc /* Source XMI: _18_5_2_3880181_1550588726081_505563_65444
                        Stereotype Component
                        UML kind: uml:Class */
                    }
                    part def 'Segment' {
                        @OfficialCSRMProfile::'Architecture Structures Profile'::'Segment';
                        doc /* Source XMI: _18_5_2_3880181_1550588745844_406707_65446
                        Stereotype Segment
                        UML kind: uml:Class */
                        part 'cubeSat' : OfficialCSRM::'Data'::'02 - CSRM Elements, Examples and Illustrations'::'8 - CSRM Population'::'8.2 - CSRM Elements'::'CubeSat' {
                            doc /* Source XMI: _18_5_2_3880181_1550854013833_859755_66079
                            Stereotype PartProperty
                            UML aggregation: composite
                            UML association: _18_5_2_3880181_1550854013833_715882_66078 */
                        }
                    }
                    part def 'CubeSat' {
                        @OfficialCSRMProfile::'Architecture Structures Profile'::'CubeSat';
                        doc /* Source XMI: _18_5_2_3880181_1550588771608_670433_65448
                        Stereotype CubeSat
                        UML kind: uml:Class */
                        part 'subsystem' : OfficialCSRM::'Data'::'02 - CSRM Elements, Examples and Illustrations'::'8 - CSRM Population'::'8.2 - CSRM Elements'::'Subsystem' {
                            doc /* Source XMI: _18_5_2_3880181_1550854065133_982773_66109
                            Stereotype PartProperty
                            UML aggregation: composite
                            UML association: _18_5_2_3880181_1550854065133_447952_66108 */
                        }
                    }
                    part def 'Stakeholder Concern' {
                        @OfficialCSRMProfile::'Concerns and Requirements Profile'::'StakeholderConcern';
                        doc /* Source XMI: _18_5_2_3880181_1550599359061_868745_64970
                        Stereotype StakeholderConcern: Text=, Id=11
                        UML kind: uml:Class */
                    }
                    part def 'Mission Objective' {
                        @OfficialCSRMProfile::'Concerns and Requirements Profile'::'MissionObjective';
                        doc /* Source XMI: _18_5_2_3880181_1550600042750_947114_65022
                        Stereotype MissionObjective: Text=, Id=13
                        UML kind: uml:Class */
                    }
                    part def 'Mission Need' {
                        @OfficialCSRMProfile::'Concerns and Requirements Profile'::'MissionNeed';
                        doc /* Source XMI: _18_5_2_3880181_1550600389421_565358_65201
                        Stereotype MissionNeed: Text=, Id=15
                        UML kind: uml:Class */
                    }
                    part def 'Mission Constraint' {
                        @OfficialCSRMProfile::'Concerns and Requirements Profile'::'MissionConstraint';
                        doc /* Source XMI: _18_5_2_3880181_1550600564395_351239_65234
                        Stereotype MissionConstraint: Text=, Id=16
                        UML kind: uml:Class */
                    }
                    requirement def 'Mission Requirement' {
                        @OfficialCSRMProfile::'Concerns and Requirements Profile'::'MissionRequirement';
                        comment /* Source XMI: _18_5_2_3880181_1550600772539_8123_65267
                        Stereotype MissionRequirement: Text=, Id=17
                        UML kind: uml:Class */
                    }
                    requirement def 'CubeSat Requirement' {
                        @OfficialCSRMProfile::'Concerns and Requirements Profile'::'CubeSatRequirement';
                        comment /* Source XMI: _18_5_2_3880181_1550602424779_130017_65119
                        Stereotype CubeSatRequirement: Text=, Id=18
                        UML kind: uml:Class */
                    }
                    requirement def 'Ground Segment Requirement' {
                        @OfficialCSRMProfile::'Concerns and Requirements Profile'::'GroundSegmentRequirement';
                        comment /* Source XMI: _18_5_2_3880181_1550602556989_900828_65153
                        Stereotype GroundSegmentRequirement: Text=, Id=19
                        UML kind: uml:Class */
                    }
                    requirement def 'Subsystem Requirement' {
                        @OfficialCSRMProfile::'Concerns and Requirements Profile'::'SubsystemRequirement';
                        comment /* Source XMI: _18_5_2_3880181_1550607961610_906101_65392
                        Stereotype SubsystemRequirement: Text=, Id=20
                        UML kind: uml:Class */
                    }
                    requirement def 'Component Requirement' {
                        @OfficialCSRMProfile::'Concerns and Requirements Profile'::'ComponentRequirement';
                        comment /* Source XMI: _18_5_2_3880181_1550618525962_835535_65372
                        Stereotype ComponentRequirement: Text=, Id=21
                        UML kind: uml:Class */
                    }
                    requirement def 'Deployer Interface Requirement' {
                        @OfficialCSRMProfile::'Concerns and Requirements Profile'::'DeployerRequirement';
                        comment /* Source XMI: _18_5_2_3880181_1550618891163_703979_65432
                        Stereotype DeployerRequirement: Text=, Id=22
                        UML kind: uml:Class */
                    }
                    part def 'MOE Specification' {
                        @OfficialCSRMProfile::'Technical Measures Profile'::'moeSpecification';
                        doc /* Source XMI: _18_5_2_3880181_1550619077859_738093_65465
                        Stereotype moeSpecification
                        UML kind: uml:Class */
                    }
                    part def 'MOP Specification' {
                        @OfficialCSRMProfile::'Technical Measures Profile'::'mopSpecification';
                        doc /* Source XMI: _18_5_2_3880181_1550619198047_529497_65498
                        Stereotype mopSpecification
                        UML kind: uml:Class */
                    }
                    part def 'TPM Specification' {
                        @OfficialCSRMProfile::'Technical Measures Profile'::'tpmSpecification';
                        doc /* Source XMI: _18_5_2_3880181_1550619326242_784480_65531
                        Stereotype tpmSpecification
                        UML kind: uml:Class */
                    }
                    part def 'Stakeholder' {
                        doc /* Source XMI: _18_5_2_3880181_1550674559952_634097_65627
                        Stereotype Stakeholder
                        UML kind: uml:Actor */
                    }
                    part def 'Enterprise' {
                        doc /* Source XMI: _18_5_2_3880181_1550853616798_253977_65631
                        Stereotype Block
                        UML kind: uml:Class */
                        part 'segment' : OfficialCSRM::'Data'::'02 - CSRM Elements, Examples and Illustrations'::'8 - CSRM Population'::'8.2 - CSRM Elements'::'Segment' {
                            doc /* Source XMI: _18_5_2_3880181_1550853988869_309320_66049
                            Stereotype PartProperty
                            UML aggregation: composite
                            UML association: _18_5_2_3880181_1550853988869_879011_66048 */
                        }
                    }
                    connection def association_28 {
                        doc /* Source XMI: _18_5_2_3880181_1550853988869_879011_66048
                        UML end details are in the source map (SysML v2 connector ends have fixed [1..1] multiplicity). */
                        end end1 : OfficialCSRM::'Data'::'02 - CSRM Elements, Examples and Illustrations'::'8 - CSRM Population'::'8.2 - CSRM Elements'::'Segment' {
                            doc /* Source XMI: _18_5_2_3880181_1550853988869_309320_66049
                            Stereotype PartProperty
                            UML end name: segment */
                        }
                        end end2 : OfficialCSRM::'Data'::'02 - CSRM Elements, Examples and Illustrations'::'8 - CSRM Population'::'8.2 - CSRM Elements'::'Enterprise' {
                            doc /* Source XMI: _18_5_2_3880181_1550853988869_679812_66050
                            UML end name: (unnamed) */
                        }
                    }
                    connection def association_29 {
                        doc /* Source XMI: _18_5_2_3880181_1550854013833_715882_66078
                        UML end details are in the source map (SysML v2 connector ends have fixed [1..1] multiplicity). */
                        end end1 : OfficialCSRM::'Data'::'02 - CSRM Elements, Examples and Illustrations'::'8 - CSRM Population'::'8.2 - CSRM Elements'::'CubeSat' {
                            doc /* Source XMI: _18_5_2_3880181_1550854013833_859755_66079
                            Stereotype PartProperty
                            UML end name: cubeSat */
                        }
                        end end2 : OfficialCSRM::'Data'::'02 - CSRM Elements, Examples and Illustrations'::'8 - CSRM Population'::'8.2 - CSRM Elements'::'Segment' {
                            doc /* Source XMI: _18_5_2_3880181_1550854013833_160129_66080
                            UML end name: (unnamed) */
                        }
                    }
                    connection def association_30 {
                        doc /* Source XMI: _18_5_2_3880181_1550854065133_447952_66108
                        UML end details are in the source map (SysML v2 connector ends have fixed [1..1] multiplicity). */
                        end end1 : OfficialCSRM::'Data'::'02 - CSRM Elements, Examples and Illustrations'::'8 - CSRM Population'::'8.2 - CSRM Elements'::'Subsystem' {
                            doc /* Source XMI: _18_5_2_3880181_1550854065133_982773_66109
                            Stereotype PartProperty
                            UML end name: subsystem */
                        }
                        end end2 : OfficialCSRM::'Data'::'02 - CSRM Elements, Examples and Illustrations'::'8 - CSRM Population'::'8.2 - CSRM Elements'::'CubeSat' {
                            doc /* Source XMI: _18_5_2_3880181_1550854065133_493175_66110
                            UML end name: (unnamed) */
                        }
                    }
                    connection def association_31 {
                        doc /* Source XMI: _18_5_2_3880181_1550854076077_525949_66138
                        UML end details are in the source map (SysML v2 connector ends have fixed [1..1] multiplicity). */
                        end end1 : OfficialCSRM::'Data'::'02 - CSRM Elements, Examples and Illustrations'::'8 - CSRM Population'::'8.2 - CSRM Elements'::'Component' {
                            doc /* Source XMI: _18_5_2_3880181_1550854076077_816754_66139
                            Stereotype PartProperty
                            UML end name: component */
                        }
                        end end2 : OfficialCSRM::'Data'::'02 - CSRM Elements, Examples and Illustrations'::'8 - CSRM Population'::'8.2 - CSRM Elements'::'Subsystem' {
                            doc /* Source XMI: _18_5_2_3880181_1550854076078_308967_66140
                            UML end name: (unnamed) */
                        }
                    }
                    part def 'Domain' {
                        doc /* Source XMI: _18_5_2_3880181_1550864112961_905200_65682
                        Stereotype Block
                        UML kind: uml:Class */
                        part 'enterprise' : OfficialCSRM::'Data'::'02 - CSRM Elements, Examples and Illustrations'::'8 - CSRM Population'::'8.2 - CSRM Elements'::'Enterprise' {
                            doc /* Source XMI: _18_5_2_3880181_1550864180508_976117_65726
                            Stereotype PartProperty
                            UML aggregation: composite
                            UML association: _18_5_2_3880181_1550864180506_915416_65725 */
                        }
                    }
                    connection def association_33 {
                        doc /* Source XMI: _18_5_2_3880181_1550864180506_915416_65725
                        UML end details are in the source map (SysML v2 connector ends have fixed [1..1] multiplicity). */
                        end end1 : OfficialCSRM::'Data'::'02 - CSRM Elements, Examples and Illustrations'::'8 - CSRM Population'::'8.2 - CSRM Elements'::'Enterprise' {
                            doc /* Source XMI: _18_5_2_3880181_1550864180508_976117_65726
                            Stereotype PartProperty
                            UML end name: enterprise */
                        }
                        end end2 : OfficialCSRM::'Data'::'02 - CSRM Elements, Examples and Illustrations'::'8 - CSRM Population'::'8.2 - CSRM Elements'::'Domain' {
                            doc /* Source XMI: _18_5_2_3880181_1550864180508_614403_65727
                            UML end name: (unnamed) */
                        }
                    }
                    part def 'Verification Activity' {
                        @OfficialCSRMProfile::'Validation and Verification Profile'::'ValidationActivity';
                        doc /* Source XMI: _19_0_2_3880181_1556292983089_714987_59210
                        Stereotype ValidationActivity
                        UML kind: uml:Class */
                    }
                    part def 'Validation Activity' {
                        @OfficialCSRMProfile::'Validation and Verification Profile'::'ValidationActivity';
                        doc /* Source XMI: _19_0_2_3880181_1556293264150_233603_59214
                        Stereotype ValidationActivity
                        UML kind: uml:Class */
                    }
                    part def 'Facility' {
                        @OfficialCSRMProfile::'Architecture Structures Profile'::'Facility';
                        doc /* Source XMI: _19_0_2_3880181_1573090171007_863579_62865
                        Stereotype Facility
                        UML kind: uml:Class */
                        part 'equipment' : OfficialCSRM::'Data'::'02 - CSRM Elements, Examples and Illustrations'::'8 - CSRM Population'::'8.2 - CSRM Elements'::'Equipment' {
                            doc /* Source XMI: _19_0_2_3880181_1573090411099_35619_63002
                            Stereotype PartProperty
                            UML aggregation: composite
                            UML association: _19_0_2_3880181_1573090411099_92226_63001 */
                        }
                    }
                    part def 'Equipment' {
                        @OfficialCSRMProfile::'Architecture Structures Profile'::'Equipment';
                        doc /* Source XMI: _19_0_2_3880181_1573090301896_609826_62904
                        Stereotype Equipment
                        UML kind: uml:Class */
                    }
                    connection def association_38 {
                        doc /* Source XMI: _19_0_2_3880181_1573090411099_92226_63001
                        UML end details are in the source map (SysML v2 connector ends have fixed [1..1] multiplicity). */
                        end end1 : OfficialCSRM::'Data'::'02 - CSRM Elements, Examples and Illustrations'::'8 - CSRM Population'::'8.2 - CSRM Elements'::'Equipment' {
                            doc /* Source XMI: _19_0_2_3880181_1573090411099_35619_63002
                            Stereotype PartProperty
                            UML end name: equipment */
                        }
                        end end2 : OfficialCSRM::'Data'::'02 - CSRM Elements, Examples and Illustrations'::'8 - CSRM Population'::'8.2 - CSRM Elements'::'Facility' {
                            doc /* Source XMI: _19_0_2_3880181_1573090411099_201790_63003
                            UML end name: (unnamed) */
                        }
                    }
                    part def 'KPP Specification' {
                        doc /* Source XMI: _19_0_2_3880181_1639147918678_388980_56340
                        Stereotype Block
                        UML kind: uml:Class */
                    }
                    part def 'MOE Requirement' {
                        doc /* Source XMI: _19_0_2_3880181_1639148359258_214632_56690
                        Stereotype Block
                        UML kind: uml:Class */
                    }
                    part def 'MOP Requrement' {
                        doc /* Source XMI: _19_0_2_3880181_1639148583992_556776_56728
                        Stereotype Block
                        UML kind: uml:Class */
                    }
                    part def 'TPM Requirement' {
                        doc /* Source XMI: _19_0_2_3880181_1639148746059_326865_56766
                        Stereotype Block
                        UML kind: uml:Class */
                    }
                    part def 'KPP Requirement' {
                        doc /* Source XMI: _19_0_2_3880181_1639148937491_346610_56805
                        Stereotype Block
                        UML kind: uml:Class */
                    }
                    package 'Behaviors' {
                        doc /* Source XMI: _19_0_2_3880181_1639184200024_281661_56448
                        UML kind: uml:Package */
                    }
                    package 'Activities' {
                        doc /* Source XMI: _19_0_2_3880181_1639184495213_480351_56552
                        UML kind: uml:Package */
                        action def 'Activities' {
                            doc /* Source XMI: _18_5_2_3880181_1550766974924_429130_65739
                            UML kind: uml:Activity */
                        }
                    }
                    package 'Use Cases' {
                        doc /* Source XMI: _19_0_2_3880181_1639184537618_681692_56553
                        UML kind: uml:Package */
                        use case def 'Use Cases' {
                            doc /* Source XMI: _18_5_2_3880181_1550621997477_139495_65979
                            UML kind: uml:UseCase */
                        }
                    }
                }
                package '8.3 - CSRM Examples and Illustrations' {
                    doc /* Source XMI: _19_0_2_3880181_1655920358094_956317_58907
                    Comment _19_0_2_3880181_1655927231335_156475_59524 (Explanation)
                    CSRM Examples and Illustrations
                    UML kind: uml:Package */
                }
            }
            package '0 - Examples and Illustrations' {
                doc /* Source XMI: _19_0_2_3880181_1639330685526_455004_58349
                UML kind: uml:Package */
            }
        }
        package '00 - CSRM Start Here' {
            doc /* Source XMI: _19_0_2_3880181_1639328897082_908495_56506
            Comment _2022x_2_2b0010b_1698610587856_938097_26243 (Explanation)
            The CSRM Profile contains the sub-profiles of the CubeSat System Reference Model (CSRM) Profile. The purpose of extensions is to add metadata, aid in dynamic reporting/analysis, validate a model's composition, and aid in grouping.
            UML kind: uml:Package */
            package 'CSRM Profile Diagrams' {
                doc /* Source XMI: _2022x_2_2b0010b_1698608748245_49474_24592
                UML kind: uml:Package */
            }
        }
    }
}
